FME workspace boringColumnXmlConersionArcGISPro.fmw

Parameters:
- SourceDataset_XML =   # Source XML File(s)
- DestDataset_GEODATABASE_FILE =   # File Geodatabase
- SKIP_DUPLICATE_BORING = Yes   # Skip Duplicate Boring

Readers:
- XML_1: XML from $(SourceDataset_XML)

Writers:
- GEODATABASE_FILE_1: GEODATABASE_FILE to $(DestDataset_GEODATABASE_FILE)

Note: 開発・保守メモ: AttributeManager 使用不可! / ArcGIS 10.4 Data Interoperability が AttributeManager をサポートしていないため。 / 不要な属性の削除や属性名の変更には / ・AttributeRemover / ・AttributeRenamer / ・BulkAttributeRenamer / 等 を使うこと。 / Custom Format としてエクスポートした後, 以下の修正をすること。 / - ソースデータセットをクリア / - 全てのライターフィーチャータイプのジオメトリタイプを fme_point に設定 / - メニュー: Writers / Redirect to FME Data Inspector チェックをオフ / カスタムフォーマット名 / ・New Custom Format Name (フォーマット識別子, *.fdsファイル名): JP_MLIT_CALS_EC_BORING_XML / ・New Custom Format Description (フォーマット全称): Japan MLIT CALS/EC Boring Information XML
標題情報 (reader XML_1)
    attributes: N値記録用具.N値記録用具_コード xml_decimal(2,0), N値記録用具.N値記録用具_名称 xml_char(1), xml_fragment xml_xml, xml_id xml_char(16), xml_matched_element xml_char(9), xml_parent_child_pos xml_char(1), xml_parent_id xml_char(1), エンジン.エンジン_単位 xml_char(1), エンジン.エンジン_能力 xml_char(1), エンジン.エンジン_名称 xml_char(9), ハンマー落下用具.ハンマー落下用具_コード xml_decimal(2,0), ハンマー落下用具.ハンマー落下用具_名称 xml_char(1), ボーリング基本情報.掘進角度 xml_decimal(5,2), ボーリング基本情報.掘進方向 xml_decimal(5,2), ボーリング基本情報.孔口標高 xml_decimal(4,2), ボーリング基本情報.総掘進長 xml_decimal(5,2), ボーリング基本情報.地盤勾配 xml_decimal(5,2), ボーリング基本情報.柱状図様式 xml_char(255), ボーリング情報.DTD_version xml_decimal(4,2), ポンプ.ポンプ_単位 xml_char(1), ポンプ.ポンプ_能力 xml_char(1), ポンプ.ポンプ_名称 xml_char(7), ローカル座標{}.座標 xml_decimal(8,3), ローカル座標{}.座標定義 xml_char(5), 経度緯度情報.緯度_度 xml_decimal(3,0), 経度緯度情報.緯度_秒 xml_decimal(7,4), 経度緯度情報.緯度_分 xml_decimal(3,0), 経度緯度情報.経度_度 xml_decimal(4,0), 経度緯度情報.経度_秒 xml_decimal(7,4), 経度緯度情報.経度_分 xml_decimal(3,0),
      経度緯度情報.取得方法コード xml_decimal(3,0), 経度緯度情報.取得方法説明 xml_char(38), 経度緯度情報.測地系 xml_char(255), 経度緯度情報.読取精度コード xml_decimal(2,0), 試錐機.試錐機_能力 xml_decimal(4,0), 試錐機.試錐機_方法 xml_decimal(2,0), 試錐機.試錐機_名称 xml_char(9), 調査位置.コード1次 xml_decimal(5,0), 調査位置.コード2次 xml_decimal(3,0), 調査位置.コード3次 xml_decimal(3,0), 調査位置.調査位置住所 xml_char(25), 調査会社.調査会社_TEL xml_char(14), 調査会社.調査会社_コア鑑定者 xml_char(9), 調査会社.調査会社_ボーリング責任者 xml_char(9), 調査会社.調査会社_現場代理人 xml_char(9), 調査会社.調査会社_主任技師 xml_char(9), 調査会社.調査会社_名称 xml_char(27), 調査基本情報.ボーリング総数 xml_decimal(3,0), 調査基本情報.ボーリング名 xml_char(4), 調査基本情報.ボーリング連番 xml_decimal(2,0), 調査基本情報.事業工事名 xml_char(23), 調査基本情報.調査対象 xml_decimal(3,0), 調査基本情報.調査名 xml_char(26), 調査基本情報.調査目的 xml_decimal(3,0), 調査期間.調査期間_開始年月日 xml_char(11), 調査期間.調査期間_終了年月日 xml_char(11), 発注機関.テクリスコード xml_decimal(9,0), 発注機関.発注機関名称 xml_char(41), 櫓種類.櫓種類コード xml_decimal(2,0), 櫓種類.櫓種類名称 xml_char(1),
      ボーリング基本情報.方位 xml_decimal(5,2), 調査会社.調査会社_主任技師_氏名 xml_char(9), 調査会社.調査会社_ボーリング責任者_地質調査技士登録番号 xml_char(1), 調査会社.調査会社_電子納品管理者_地質情報管理士登録番号 xml_decimal(6,0), ボーリング基本情報.角度 xml_decimal(5,2), 調査会社.調査会社_現場代理人_氏名 xml_char(9), ボーリング基本情報.総削孔長 xml_decimal(5,2), 調査会社.調査会社_コア鑑定者_氏名 xml_char(9), 調査会社.調査会社_電子納品管理者_氏名 xml_char(9), 調査会社.調査会社_現場代理人_地質調査技士登録番号 xml_char(1), 調査会社.調査会社_ボーリング責任者_氏名 xml_char(9), 調査会社.調査会社_主任技師_地質調査技士登録番号 xml_decimal(6,0), 調査会社.調査会社_コア鑑定者_地質調査技士登録番号 xml_char(1)
    -> AttributeRemover
AttributeRemover
    REMOVE_ATTRS = xml_fragment,xml_parent_child_pos,xml_matched_element,xml_parent_id,xml_id
    -> BulkAttributeTrimmerArcGISProVer
BulkAttributeTrimmerArcGISProVer
    -> AttributeValidator
AttributeValidator
    TABLE = ボーリング情報.DTD_version;IN;2.10,3.00,4.00/経度緯度情報.経度_分,経度緯度情報.緯度_分,ボーリング基本情報.孔口標高,経度緯度情報.経度_秒,経度緯度情報.経度_度,経度緯度情報.緯度_秒,経度緯度情報.緯度_度;TYPE;DOUBLE/調査基本情報.ボーリング連番,経度緯度情報.測地系;TYPE;INT/経度緯度情報.測地系;RANGE;[0,2]
    PASSED -> BulkAttributeRenamer_3
    FAILED -> TclCaller
TclCaller
    SRC:
      proc logMessage1 {} {
          FME_LogMessage fme_warn "DTDバージョン, ボーリング連番, 経度緯度, 測地系, あるいは孔口標高の値または書式が不正なため, 次のファイルは読み込めません: [FME_GetAttribute fme_dataset]"
      }
    TCLPROG = logMessage1
BulkAttributeRenamer_3
    ATTRCHOICE = All Attributes
    MODE_CHOICE = RENAME
    PATTERN_ACTION_DISP = PCREGEXPREPLACE
    REPLACE_PATTERN = ^[^\{\}]+?\.(.+)$
    REPLACE_STR = \1
    -> BulkAttributeRenamer_4
BulkAttributeRenamer_4
    ATTRCHOICE = Selected Attributes
    ATTRLIST = 調査会社_現場代理人 調査会社_電子納品管理者_地質情報管理士登録番号 調査会社_現場代理人_氏名 調査会社_コア鑑定者_地質調査技士登録番号 調査会社_コア鑑定者 調査会社_コア鑑定者_氏名 調査会社_ボーリング責任者 調査会社_ボーリング責任者_地質調査技士登録番号 調査会社_電子納品管理者_氏名 調査会社_主任技師 調査会社_主任技師_氏名 調査会社_現場代理人_地質調査技士登録番号 調査会社_主任技師_地質調査技士登録番号 調査会社_ボーリング責任者_氏名
    CASE_DISP = YES
    MODE_CHOICE = RENAME
    PATTERN_ACTION_DISP = REMOVEPREFIX
    REPLACE_STR = 調査会社_
    -> AttributeRenamer
AttributeRenamer
    ATTR_TABLE:
      RENAME_SET_DEFAULT 主任技師 > 主任技師_氏名
      RENAME_SET_DEFAULT 現場代理人 > 現場代理人_氏名
      RENAME_SET_DEFAULT コア鑑定者 > コア鑑定者_氏名
      RENAME_SET_DEFAULT ボーリング責任者 > ボーリング責任者_氏名
      RENAME_SET_DEFAULT 総掘進長 > 総削孔長
      RENAME_SET_DEFAULT 掘進角度 > 角度
      RENAME_SET_DEFAULT 掘進方向 > 方位
    MISSING_INPUT_ATTRS = PRESERVE
    -> StringConcatenator
Note: "ボーリングID" 作成
StringConcatenator
    ACTION = Create New Attribute
    PARM_LINE = @Format(%03d,@Value(経度_度))@Format(%02d,@Value(経度_分))@Format(%06d,@Evaluate(@round(@Value(経度_秒)*10000)))_@Format(%02d,@Value(緯度_度))@Format(%02d,@Value(緯度_分))@Format(%06d,@Evaluate(@round(@Value(緯度_秒)*10000)))_@Format(%02d,@Value(測地系))_@Substring(@Value(調査名),0,30)_@Substring(@Value(ボーリング名),0,30)_@Format(%04d,@Value(ボーリング連番))
    VAL_ATTR = ボーリングID
    -> Tester
Tester
    BOOL_OP = OR
    TEST_CLAUSE = TEST $(SKIP_DUPLICATE_BORING) != Yes
    TEST_MODE = TEST
    PASSED -> VertexCreator
    FAILED -> Sampler
Sampler
    GROUP_BY = ボーリングID
    RATE = 1
    SAMPLE_MODE = No
    SAMPLE_TYPE_LONG = First N Features
    SAMPLED -> VertexCreator
    NOT_SAMPLED -> TclCaller_2
DateFormatter
    DATE_ATTR = 調査期間_開始年月日,調査期間_終了年月日
    FMT = FME Date (%Y%m%d)
    INVALID_DATE_VALUE = FME_NULL_VALUE
    SRCFMT = %Y-%m-%d
    -> AttributeKeeper_2
    -> 標題情報 (writer GEODATABASE_FILE_1)
AttributeKeeper_2
    CREATE_BULK_MODE_FEATURES = No
    KEEP_ATTRS = DTD_version,fme_dataset,ボーリングID,孔口標高
    -> junction_1
    -> FeatureMerger_2 [SUPPLIER]
junction_1: AttributeRemover
    -> FeatureMerger_A [SUPPLIER]
    -> FeatureMerger_A_4 [SUPPLIER]
    -> FeatureMerger_A_5 [SUPPLIER]
    -> FeatureMerger_A_6 [SUPPLIER]
    -> FeatureMerger_A_8 [SUPPLIER]
    -> FeatureMerger_A_9 [SUPPLIER]
    -> FeatureMerger_A_2 [SUPPLIER]
    -> FeatureMerger_B_2 [SUPPLIER]
    -> FeatureMerger_B_5 [SUPPLIER]
    -> FeatureMerger_B_8 [SUPPLIER]
    -> FeatureMerger_B_11 [SUPPLIER]
    -> junction_2
    -> FeatureMerger_A_3 [SUPPLIER]
    -> FeatureMerger_B_14 [SUPPLIER]
    -> FeatureMerger_B_16 [SUPPLIER]
    -> FeatureMerger_B_18 [SUPPLIER]
junction_2: AttributeRemover
    -> FeatureMerger_C [SUPPLIER]
    -> FeatureMerger_C_2 [SUPPLIER]
    -> FeatureMerger_C_3 [SUPPLIER]
    -> FeatureMerger_C_4 [SUPPLIER]
    -> FeatureMerger_C_5 [SUPPLIER]
    -> FeatureMerger_C_6 [SUPPLIER]
    -> FeatureMerger_C_7 [SUPPLIER]
    -> FeatureMerger_C_8 [SUPPLIER]
    -> FeatureMerger_C_9 [SUPPLIER]
    -> FeatureMerger_D [SUPPLIER]
    -> FeatureMerger_D_2 [SUPPLIER]
    -> FeatureMerger_D_3 [SUPPLIER]
    -> FeatureMerger_D_4 [SUPPLIER]
    -> FeatureMerger_D_8 [SUPPLIER]
    -> FeatureMerger_D_5 [SUPPLIER]
    -> FeatureMerger_D_6 [SUPPLIER]
    -> FeatureMerger_D_7 [SUPPLIER]
    -> FeatureMerger_D_13 [SUPPLIER]
    -> FeatureMerger_D_12 [SUPPLIER]
    -> FeatureMerger_D_11 [SUPPLIER]
    -> FeatureMerger_D_10 [SUPPLIER]
    -> FeatureMerger_D_9 [SUPPLIER]
    -> junction_3
junction_3: AttributeRemover
    -> FeatureMerger_E [SUPPLIER]
    -> FeatureMerger_E_2 [SUPPLIER]
    -> FeatureMerger_E_3 [SUPPLIER]
    -> FeatureMerger_E_4 [SUPPLIER]
    -> FeatureMerger_E_5 [SUPPLIER]
    -> FeatureMerger_E_6 [SUPPLIER]
    -> FeatureMerger_E_7 [SUPPLIER]
    -> FeatureMerger_Z [SUPPLIER]
    -> FeatureMerger_Z_2 [SUPPLIER]
標題情報 (writer GEODATABASE_FILE_1)
    attributes: ボーリングID char(100), DTD_version char(8), 事業工事名 char(100), 調査名 char(100), 調査目的 char(4), 調査対象 char(4), ボーリング名 char(100), ボーリング総数 integer, ボーリング連番 integer, 経度_度 smallint, 経度_分 smallint, 経度_秒 double(8,4), 緯度_度 smallint, 緯度_分 smallint, 緯度_秒 double(8,4), 取得方法コード char(4), 取得方法説明 char(100), 読取精度コード char(2), 測地系 char(4), ローカル座標___座標定義 char(2048), ローカル座標___座標 char(2048), 調査位置住所 char(200), コード1次 char(4), コード2次 char(2), コード3次 char(2), 発注機関名称 char(200), テクリスコード char(100), 調査期間_開始年月日 date, 調査期間_終了年月日 date, 調査会社_名称 char(100),
      調査会社_TEL char(20), 主任技師_氏名 char(20), 主任技師_地質調査技士登録番号 char(10), 現場代理人_氏名 char(20), 現場代理人_地質調査技士登録番号 char(10), コア鑑定者_氏名 char(20), コア鑑定者_地質調査技士登録番号 char(10), ボーリング責任者_氏名 char(20), ボーリング責任者_地質調査技士登録番号 char(10), 電子納品管理者_氏名 char(20), 電子納品管理者_地質情報管理士登録番号 char(10), 孔口標高 double(8,2), 総削孔長 double(8,2), 柱状図様式 char(4), 角度 double(8,2), 方位 double(8,2), 地盤勾配 double(8,2), 試錐機_名称 char(100), 試錐機_能力 double, 試錐機_方法 char(4), エンジン_名称 char(100), エンジン_能力 double, エンジン_単位 char(10), ハンマー落下用具_コード char(2), ハンマー落下用具_名称 char(100), N値記録用具_コード char(2), N値記録用具_名称 char(100), ポンプ_名称 char(100), ポンプ_能力 double, ポンプ_単位 char(10),
      櫓種類コード char(2), 櫓種類名称 char(100)
TclCaller_2
    SRC:
      proc logMessage2 {} {
          FME_LogMessage fme_warn "先に読み込んだXML文書から取得したボーリングID (経度緯度, 測地系, 調査名, ボーリング名, ボーリング連番) と重複するため, 次のXML文書はスキップします: [FME_GetAttribute fme_dataset]"
      }
    TCLPROG = logMessage2
岩級区分判定表 (reader XML_1)
    attributes: xml_fragment xml_xml, xml_id xml_char(26), xml_matched_element xml_char(15), xml_parent_child_pos xml_char(1), xml_parent_id xml_char(1), ボーリング情報.DTD_version xml_decimal(4,2), 岩級区分判定表_項目名{} xml_char(25), 岩級区分判定表_判定{}.岩級区分判定表_コード xml_decimal(4,0), 岩級区分判定表_判定{}.岩級区分判定表_記号 xml_char(3), 岩級区分判定表_判定{}.岩級区分判定表_説明{} xml_char(78)
    -> AttributeRemover_B_8
AttributeRemover_B_8
    REMOVE_ATTRS = xml_parent_child_pos,ボーリング情報.DTD_version,xml_parent_id,xml_id,xml_fragment,xml_matched_element
    -> ListExploder_B_2
ListExploder_B_2
    ATTR_ACCUM_MODE = Merge List Attributes
    ATTR_CONFLICT_RES = Use List Attribute Values
    LIST_ATTR = 岩級区分判定表_判定{}
    ELEMENTS -> BulkAttributeRenamer_B_8
BulkAttributeRenamer_B_8
    ATTRCHOICE = All Attributes
    MODE_CHOICE = RENAME
    PATTERN_ACTION_DISP = PCREGEXPREPLACE
    REPLACE_PATTERN = ^岩級区分判定表_(項目名|説明)(\{\d*\})$
    REPLACE_STR = 説明\2.\1
    -> TclCaller_B_2
TclCaller_B_2
    SRC:
      proc modifyGankyuKubunTable {} {
          set itemList {}
          for {set numItem 0} {[FME_AttributeExists "説明{$numItem}.項目名"]} {incr numItem} {
              lappend itemList [FME_GetAttribute "説明{$numItem}.項目名"]
          }
          for {set numDesc 0} {[FME_AttributeExists "説明{$numDesc}.説明"]} {incr numDesc} {}
          if {![string equal [FME_GetAttribute "説明{0}.項目名"] "色調"] && $numItem < $numDesc} {
              set itemList [linsert $itemList 0 "色調"]
              set numItem [llength $itemList]
              for {set i 0} {$i < $numItem} {incr i} {
                  FME_SetAttribute "説明{$i}.項目名" [lindex $itemList $i]
              }
          }
          if {$numItem < $numDesc} {
              for {} {$numItem < $numDesc} {incr numItem} {
                  FME_UnsetAttributes "説明{$numItem}.説明"
                  incr numItem
              }
          } elseif {$numDesc < $numItem} {
              for {} {$numDesc < $numItem} {incr numDesc} {
                  FME_SetAttribute "説明{$numDesc}.説明" ""
              }
          }
      }
    TCLPROG = modifyGankyuKubunTable
    -> FeatureMerger_B_17 [SUPPLIER]
破砕度判定表 (reader XML_1)
    attributes: xml_fragment xml_xml, xml_id xml_char(24), xml_matched_element xml_char(13), xml_parent_child_pos xml_char(1), xml_parent_id xml_char(1), ボーリング情報.DTD_version xml_decimal(4,2), 破砕度判定表_項目名{} xml_char(15), 破砕度判定表_判定{}.破砕度判定表_コード xml_decimal(4,0), 破砕度判定表_判定{}.破砕度判定表_記号 xml_char(5), 破砕度判定表_判定{}.破砕度判定表_説明{} xml_char(25)
    -> AttributeRemover_B_6
AttributeRemover_B_6
    REMOVE_ATTRS = xml_parent_child_pos,ボーリング情報.DTD_version,xml_parent_id,xml_id,xml_fragment,xml_matched_element
    -> ListExploder_B
ListExploder_B
    ATTR_ACCUM_MODE = Merge List Attributes
    ATTR_CONFLICT_RES = Use List Attribute Values
    LIST_ATTR = 破砕度判定表_判定{}
    ELEMENTS -> BulkAttributeRenamer_B_6
BulkAttributeRenamer_B_6
    ATTRCHOICE = All Attributes
    MODE_CHOICE = RENAME
    PATTERN_ACTION_DISP = PCREGEXPREPLACE
    REPLACE_PATTERN = ^破砕度判定表_(項目名|説明)({\d*})$
    REPLACE_STR = 説明\2.\1
    -> TclCaller_B
TclCaller_B
    SRC:
      proc modifyHasaidoTable {} {
          for {set i 0} {[FME_AttributeExists "説明{$i}.項目名"]} {incr i} {
              if {![FME_AttributeExists "説明{$i}.説明"]} {
                  FME_SetAttribute "説明{$i}.説明" ""
              }
          }
          for {} {[FME_AttributeExists "説明{$i}.説明"]} {incr i} {
              FME_UnsetAttributes "説明{$i}.説明"
          }
      }
    TCLPROG = modifyHasaidoTable
    -> FeatureMerger_B_15 [SUPPLIER]
Note: DTD version 3.00, 4.00
基礎情報 (reader XML_1)
    attributes: xml_fragment xml_xml, xml_id xml_char(16), xml_matched_element xml_char(9), xml_parent_child_pos xml_char(1), xml_parent_id xml_char(1), ボーリング情報.DTD_version xml_decimal(4,2), 適用規格{} xml_char(16), 公開フラグ.公開フラグ_備考 xml_char(1), 公開フラグ.公開フラグ_コード xml_decimal(2,0)
    -> FeatureMerger_2 [REQUESTOR]
FeatureMerger_2
    ATTR_ACCUM_MODE = Merge Supplier
    ATTR_CONFLICT_RES = Use Requestor
    IGNORE_NULLS = No
    JOIN_KEYS = @Value(fme_dataset) @Value(fme_dataset) AUTO
    MERGE_TYPE = Attributes Only
    PROCESS_DUPS = NO
    REJECT_NULL_MISSING_KEYS = No
    SUPPLIERS_FIRST = No
    MERGED -> AttributeRemover_2
AttributeRemover_2
    REMOVE_ATTRS = xml_id,xml_matched_element,xml_parent_id,xml_parent_child_pos,ボーリング情報.DTD_version,xml_fragment
    -> BulkAttributeRenamer_5
BulkAttributeRenamer_5
    ATTRCHOICE = Selected Attributes
    ATTRLIST = 公開フラグ.公開フラグ_コード 公開フラグ.公開フラグ_備考
    CASE_DISP = YES
    MODE_CHOICE = RENAME
    PATTERN_ACTION_DISP = REMOVEPREFIX
    REPLACE_STR = 公開フラグ.
    -> AttributeManager
AttributeManager
    ATTR_TABLE = SET_TO 適用規格 = @Value(適用規格{0})
    USER_EXPOSED_ATTRIBUTES = 適用規格
    -> BulkAttributeTrimmerArcGISProVer_2
BulkAttributeTrimmerArcGISProVer_2
    -> 基礎情報 (writer GEODATABASE_FILE_1)
基礎情報 (writer GEODATABASE_FILE_1)
    attributes: ボーリングID char(100), DTD_version char(8), 孔口標高 double(8,2), 適用規格 char(2048), 公開フラグ_コード char(2), 公開フラグ_備考 char(100)
標準貫入試験 (reader XML_1)
    attributes: xml_fragment xml_xml, xml_id xml_char(23), xml_matched_element xml_char(13), xml_parent_child_pos xml_char(1), xml_parent_id xml_char(1), ボーリング情報.DTD_version xml_decimal(4,2), 標準貫入試験_0_10貫入量 xml_decimal(3,0), 標準貫入試験_0_10打撃回数 xml_decimal(3,0), 標準貫入試験_10_20貫入量 xml_char(3), 標準貫入試験_10_20打撃回数 xml_char(3), 標準貫入試験_20_30貫入量 xml_char(3), 標準貫入試験_20_30打撃回数 xml_char(3), 標準貫入試験_開始深度 xml_decimal(5,2), 標準貫入試験_合計貫入量 xml_char(255), 標準貫入試験_合計打撃回数 xml_decimal(3,0), 標準貫入試験_備考 xml_char(13), 標準貫入試験_100_200貫入量 xml_char(4), 標準貫入試験_0_100貫入量 xml_decimal(4,0), 標準貫入試験_100_200打撃回数 xml_char(3), 標準貫入試験_0_100打撃回数 xml_decimal(3,0), 標準貫入試験_200_300貫入量 xml_char(4), 標準貫入試験_200_300打撃回数 xml_char(3)
    -> BulkAttributeRenamer_A_3
BulkAttributeRenamer_A_3
    ATTRCHOICE = Selected Attributes
    ATTRLIST = 標準貫入試験_10_20打撃回数 標準貫入試験_20_30貫入量 標準貫入試験_20_30打撃回数 標準貫入試験_100_200貫入量 標準貫入試験_200_300貫入量 標準貫入試験_200_300打撃回数 標準貫入試験_合計貫入量 標準貫入試験_0_10貫入量 標準貫入試験_備考 標準貫入試験_10_20貫入量 標準貫入試験_100_200打撃回数 標準貫入試験_開始深度 標準貫入試験_0_100打撃回数 標準貫入試験_0_10打撃回数 標準貫入試験_合計打撃回数 標準貫入試験_0_100貫入量
    CASE_DISP = YES
    MODE_CHOICE = RENAME
    PATTERN_ACTION_DISP = REMOVEPREFIX
    REPLACE_STR = 標準貫入試験_
    -> Tester_A
Tester_A
    BOOL_OP = OR
    TEST_CLAUSE:
      TEST @Value(ボーリング情報.DTD_version) = 2.10
      TEST @Value(ボーリング情報.DTD_version) = 3.00
    TEST_MODE = TEST
    PASSED -> TclCaller_A
    FAILED -> AttributeRemover_A_4
TclCaller_A
    SRC:
      proc convKannyuryou {} {
          foreach attr [list "0_10貫入量" "10_20貫入量" "20_30貫入量" "合計貫入量"] {
              set val [FME_GetAttribute $attr]
              if {[string is double -strict $val]} {
                  FME_SetAttribute $attr [expr $val*10]
              }
          }
      }
    TCLPROG = convKannyuryou
    -> AttributeRenamer_A_2
AttributeRenamer_A_2
    ATTR_TABLE:
      RENAME_SET_DEFAULT 0_10打撃回数 > 打撃回数_0_100
      RENAME_SET_DEFAULT 0_10貫入量 > 貫入量_0_100
      RENAME_SET_DEFAULT 10_20打撃回数 > 打撃回数_100_200
      RENAME_SET_DEFAULT 10_20貫入量 > 貫入量_100_200
      RENAME_SET_DEFAULT 20_30打撃回数 > 打撃回数_200_300
      RENAME_SET_DEFAULT 20_30貫入量 > 貫入量_200_300
    MISSING_INPUT_ATTRS = PRESERVE
    -> AttributeRemover_A_4
AttributeRemover_A_4
    REMOVE_ATTRS = 20_30打撃回数,xml_parent_id,xml_fragment,10_20貫入量,xml_id,20_30貫入量,ボーリング情報.DTD_version,0_10貫入量,10_20打撃回数,0_10打撃回数,xml_parent_child_pos,xml_matched_element
    -> FeatureMerger_A_4 [REQUESTOR]
FeatureMerger_A_4
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_A_4
BulkAttributeTrimmerArcGISProVer_A_4
    -> 3DForcer_A_4
3DForcer_A_4
    KEEPZVAL = No
    ZVALATTR = @Value(孔口標高)-@Value(開始深度)
    -> コア情報_標準貫入試験 (writer GEODATABASE_FILE_1)
コア情報_標準貫入試験 (writer GEODATABASE_FILE_1)
    attributes: ボーリングID char(100), DTD_version char(8), 孔口標高 double(8,2), 開始深度 double(8,2), 打撃回数_0_100 smallint, 貫入量_0_100 smallint, 打撃回数_100_200 smallint, 貫入量_100_200 smallint, 打撃回数_200_300 smallint, 貫入量_200_300 smallint, 合計打撃回数 smallint, 合計貫入量 smallint, 備考 char(100)
ルジオン試験 (reader XML_1)
    attributes: xml_fragment xml_xml, xml_id xml_char(23), xml_matched_element xml_char(13), xml_parent_child_pos xml_char(1), xml_parent_id xml_char(1), ボーリング情報.DTD_version xml_decimal(4,2), ルジオン試験_ルジオン値 xml_decimal(5,2), ルジオン試験_ルジオン値区分 xml_decimal(2,0), ルジオン試験_圧力開始点 xml_decimal(5,3), ルジオン試験_圧力管理方法 xml_char(1), ルジオン試験_圧力管理方法コード xml_decimal(2,0), ルジオン試験_圧力最大スケール xml_decimal(2,0), ルジオン試験_下端深度 xml_decimal(5,2), ルジオン試験_限界圧力 xml_decimal(5,3), ルジオン試験_試験番号 xml_decimal(5,0), ルジオン試験_上端深度 xml_decimal(5,2), ルジオン試験_注入量開始点 xml_decimal(4,2), ルジオン試験_注入量最大スケール xml_decimal(3,0)
    -> BulkAttributeRenamer_A_5
BulkAttributeRenamer_A_5
    ATTRCHOICE = Selected Attributes
    ATTRLIST = ルジオン試験_圧力最大スケール ルジオン試験_下端深度 ルジオン試験_ルジオン値 ルジオン試験_圧力管理方法 ルジオン試験_試験番号 ルジオン試験_圧力管理方法コード ルジオン試験_ルジオン値区分 ルジオン試験_上端深度 ルジオン試験_限界圧力 ルジオン試験_圧力開始点 ルジオン試験_注入量最大スケール ルジオン試験_注入量開始点
    CASE_DISP = YES
    MODE_CHOICE = RENAME
    PATTERN_ACTION_DISP = REMOVEPREFIX
    REPLACE_STR = ルジオン試験_
    -> AttributeKeeper_A
    -> AttributeRemover_A_6
AttributeRemover_A_6
    REMOVE_ATTRS = xml_parent_id,xml_fragment,xml_id,ボーリング情報.DTD_version,xml_parent_child_pos,xml_matched_element
    -> FeatureMerger_A_6 [REQUESTOR]
FeatureMerger_A_6
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_A_6
BulkAttributeTrimmerArcGISProVer_A_6
    -> 3DForcer_A_6
3DForcer_A_6
    KEEPZVAL = No
    ZVALATTR = @Value(孔口標高)-@Value(下端深度)
    -> コア情報_ルジオン試験 (writer GEODATABASE_FILE_1)
コア情報_ルジオン試験 (writer GEODATABASE_FILE_1)
    attributes: ボーリングID char(100), DTD_version char(8), 孔口標高 double(8,2), 試験番号 char(4), 上端深度 double(8,2), 下端深度 double(8,2), 圧力管理方法コード char(2), 圧力管理方法 char(100), 圧力最大スケール smallint, 注入量最大スケール smallint, 圧力開始点 double(8,3), 注入量開始点 double(8,2), ルジオン値区分 char(2), ルジオン値 double(8,2), 限界圧力 double(8,3)
AttributeKeeper_A
    CREATE_BULK_MODE_FEATURES = No
    KEEP_ATTRS = 下端深度,試験番号,fme_dataset,上端深度
    -> FeatureMerger_A_7 [SUPPLIER]
FeatureMerger_B_3
    ATTR_ACCUM_MODE = Merge Supplier
    ATTR_CONFLICT_RES = Use Requestor
    GROUP_BY = fme_dataset
    IGNORE_NULLS = No
    JOIN_KEYS = @Value(コア形状区分_コア形状区分) @Value(コア形状区分判定表_コード) AUTO
    MERGE_TYPE = Attributes Only
    PROCESS_DUPS = NO
    REJECT_NULL_MISSING_KEYS = No
    SUPPLIERS_FIRST = No
    MERGED -> BulkAttributeRenamer_B_2
    UNMERGED_REQUESTOR -> BulkAttributeRenamer_B_2
FeatureMerger_B_6
    ATTR_ACCUM_MODE = Merge Supplier
    ATTR_CONFLICT_RES = Use Requestor
    GROUP_BY = fme_dataset
    IGNORE_NULLS = No
    JOIN_KEYS = @Value(割れ目区分_割れ目区分) @Value(割れ目区分判定表_コード) AUTO
    MERGE_TYPE = Attributes Only
    PROCESS_DUPS = NO
    REJECT_NULL_MISSING_KEYS = No
    SUPPLIERS_FIRST = No
    MERGED -> BulkAttributeRenamer_B_3
    UNMERGED_REQUESTOR -> BulkAttributeRenamer_B_3
FeatureMerger_B_9
    ATTR_ACCUM_MODE = Merge Supplier
    ATTR_CONFLICT_RES = Use Requestor
    GROUP_BY = fme_dataset
    IGNORE_NULLS = No
    JOIN_KEYS = @Value(風化区分_風化区分) @Value(風化区分判定表_コード) AUTO
    MERGE_TYPE = Attributes Only
    PROCESS_DUPS = NO
    REJECT_NULL_MISSING_KEYS = No
    SUPPLIERS_FIRST = No
    MERGED -> BulkAttributeRenamer_B_4
    UNMERGED_REQUESTOR -> BulkAttributeRenamer_B_4
FeatureMerger_B_12
    ATTR_ACCUM_MODE = Merge Supplier
    ATTR_CONFLICT_RES = Use Requestor
    GROUP_BY = fme_dataset
    IGNORE_NULLS = No
    JOIN_KEYS = @Value(変質区分_変質区分) @Value(変質区分判定表_コード) AUTO
    MERGE_TYPE = Attributes Only
    PROCESS_DUPS = NO
    REJECT_NULL_MISSING_KEYS = No
    SUPPLIERS_FIRST = No
    MERGED -> BulkAttributeRenamer_B_5
    UNMERGED_REQUESTOR -> BulkAttributeRenamer_B_5
標準貫入試験詳細データ (reader XML_1)
    attributes: xml_fragment xml_xml, xml_id xml_char(33), xml_matched_element xml_char(23), xml_parent_child_pos xml_char(1), xml_parent_id xml_char(1), ボーリング情報.DTD_version xml_decimal(4,2), 標準貫入試験詳細データ_開始深度 xml_decimal(4,2), 標準貫入試験詳細データ_打撃{}.標準貫入試験詳細データ_貫入量 xml_decimal(4,0), 標準貫入試験詳細データ_打撃{}.標準貫入試験詳細データ_打撃回数 xml_decimal(2,0), 標準貫入試験詳細データ_打撃{}.標準貫入試験詳細データ_備考 xml_char(1), 標準貫入試験詳細データ_打撃{}.標準貫入試験詳細データ_累積貫入量 xml_decimal(4,0)
    -> AttributeRemover_A_5
AttributeRemover_A_5
    REMOVE_ATTRS = xml_matched_element,xml_fragment,ボーリング情報.DTD_version,xml_parent_id,xml_parent_child_pos,xml_id
    -> ListExploder_A
ListExploder_A
    ATTR_ACCUM_MODE = Merge List Attributes
    ATTR_CONFLICT_RES = Use List Attribute Values
    LIST_ATTR = 標準貫入試験詳細データ_打撃{}
    ELEMENTS -> BulkAttributeRenamer_A_4
BulkAttributeRenamer_A_4
    ATTRCHOICE = Selected Attributes
    ATTRLIST = 標準貫入試験詳細データ_開始深度 標準貫入試験詳細データ_打撃回数 標準貫入試験詳細データ_備考 標準貫入試験詳細データ_貫入量 標準貫入試験詳細データ_累積貫入量
    CASE_DISP = YES
    MODE_CHOICE = RENAME
    PATTERN_ACTION_DISP = REMOVEPREFIX
    REPLACE_STR = 標準貫入試験詳細データ_
    -> FeatureMerger_A_5 [REQUESTOR]
FeatureMerger_A_5
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_A_5
BulkAttributeTrimmerArcGISProVer_A_5
    -> 3DForcer_A_5
3DForcer_A_5
    KEEPZVAL = No
    ZVALATTR = @Value(孔口標高)-@Value(開始深度)
    -> コア情報_標準貫入試験詳細データ (writer GEODATABASE_FILE_1)
コア情報_標準貫入試験詳細データ (writer GEODATABASE_FILE_1)
    attributes: ボーリングID char(100), DTD_version char(8), 孔口標高 double(8,2), 開始深度 double(8,2), 打撃回数 smallint, 貫入量 smallint, 累積貫入量 smallint, 備考 char(100)
ルジオン試験詳細データ (reader XML_1)
    attributes: xml_fragment xml_xml, xml_id xml_char(33), xml_matched_element xml_char(23), xml_parent_child_pos xml_char(1), xml_parent_id xml_char(1), ボーリング情報.DTD_version xml_decimal(4,2), ルジオン試験詳細データ_試験番号 xml_decimal(5,0), ルジオン試験詳細データ_注入量 xml_decimal(5,2), ルジオン試験詳細データ_有効圧力 xml_decimal(5,3)
    -> BulkAttributeRenamer_A_6
BulkAttributeRenamer_A_6
    ATTRCHOICE = Selected Attributes
    ATTRLIST = ルジオン試験詳細データ_試験番号 ルジオン試験詳細データ_有効圧力 ルジオン試験詳細データ_注入量
    CASE_DISP = YES
    MODE_CHOICE = RENAME
    PATTERN_ACTION_DISP = REMOVEPREFIX
    REPLACE_STR = ルジオン試験詳細データ_
    -> FeatureMerger_A_7 [REQUESTOR]
FeatureMerger_A_7
    ATTR_ACCUM_MODE = Merge Supplier
    ATTR_CONFLICT_RES = Use Requestor
    GROUP_BY = fme_dataset
    IGNORE_NULLS = No
    JOIN_KEYS = @Value(試験番号) @Value(試験番号) AUTO
    MERGE_TYPE = Attributes Only
    PROCESS_DUPS = NO
    REJECT_NULL_MISSING_KEYS = No
    SUPPLIERS_FIRST = No
    MERGED -> AttributeRemover_A_7
AttributeRemover_A_7
    REMOVE_ATTRS = xml_parent_id,xml_fragment,xml_id,ボーリング情報.DTD_version,xml_parent_child_pos,xml_matched_element
    -> FeatureMerger_A_8 [REQUESTOR]
FeatureMerger_A_8
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_A_7
BulkAttributeTrimmerArcGISProVer_A_7
    -> 3DForcer_A_7
3DForcer_A_7
    KEEPZVAL = No
    ZVALATTR = @Value(孔口標高)-@Value(下端深度)
    -> コア情報_ルジオン試験詳細データ (writer GEODATABASE_FILE_1)
コア情報_ルジオン試験詳細データ (writer GEODATABASE_FILE_1)
    attributes: ボーリングID char(100), DTD_version char(8), 孔口標高 double(8,2), 試験番号 char(4), 上端深度 double(8,2), 下端深度 double(8,2), 有効圧力 double(8,3), 注入量 double(8,2)
FeatureMerger_B_4
    ATTR_ACCUM_MODE = Merge Supplier
    ATTR_CONFLICT_RES = Use Requestor
    GROUP_BY = fme_dataset
    IGNORE_NULLS = No
    JOIN_KEYS = @Value(ボーリングコアの形状区分_ボーリングコアの形状区分) @Value(ボーリングコアの形状区分判定表_コード) AUTO
    MERGE_TYPE = Attributes Only
    PROCESS_DUPS = NO
    REJECT_NULL_MISSING_KEYS = No
    SUPPLIERS_FIRST = No
    MERGED -> BulkAttributeRenamer_B_2
    UNMERGED_REQUESTOR -> BulkAttributeRenamer_B_2
BulkAttributeRenamer_B_2
    ATTRCHOICE = Selected Attributes
    ATTRLIST = コア形状区分判定表_記号 ボーリングコアの形状区分_下端深度 ボーリングコアの形状区分判定表_説明 ボーリングコアの形状区分判定表_コード ボーリングコアの形状区分判定表_記号 ボーリングコアの形状区分_ボーリングコアの形状区分 ボーリングコアの形状区分判定表_区分 コア形状区分_コア形状区分 コア形状区分_下端深度 コア形状区分判定表_コード コア形状区分判定表_区分 コア形状区分判定表_説明
    MODE_CHOICE = RENAME
    PATTERN_ACTION_DISP = PCREGEXPREPLACE
    REPLACE_PATTERN = ^.+?_(.+)$
    REPLACE_STR = \1
    -> AttributeRemover_B_2
AttributeRemover_B_2
    REMOVE_ATTRS = xml_parent_id,xml_fragment,xml_parent_child_pos,xml_id,ボーリング情報.DTD_version,xml_matched_element,ボーリングコアの形状区分,コア形状区分
    -> FeatureMerger_B_5 [REQUESTOR]
FeatureMerger_B_5
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_B_2
BulkAttributeTrimmerArcGISProVer_B_2
    -> 3DForcer_B_2
3DForcer_B_2
    KEEPZVAL = No
    ZVALATTR = @Value(孔口標高)-@Value(下端深度)
    -> コア情報_ボーリングコアの形状区分 (writer GEODATABASE_FILE_1)
コア情報_ボーリングコアの形状区分 (writer GEODATABASE_FILE_1)
    attributes: ボーリングID char(100), DTD_version char(8), 孔口標高 double(8,2), 下端深度 double(8,2), コード char(4), 記号 char(10), 区分 char(20), 説明 char(200)
硬軟区分 (reader XML_1)
    attributes: xml_fragment xml_xml, xml_id xml_char(19), xml_matched_element xml_char(9), xml_parent_child_pos xml_char(1), xml_parent_id xml_char(1), ボーリング情報.DTD_version xml_decimal(4,2), 硬軟区分_下端深度 xml_decimal(4,2), 硬軟区分_硬軟区分 xml_decimal(4,0)
    -> FeatureMerger_B [REQUESTOR]
硬軟区分判定表 (reader XML_1)
    attributes: xml_fragment xml_xml, xml_id xml_char(25), xml_matched_element xml_char(15), xml_parent_child_pos xml_char(1), xml_parent_id xml_char(1), ボーリング情報.DTD_version xml_decimal(4,2), 硬軟区分判定表_コード xml_decimal(4,0), 硬軟区分判定表_記号 xml_char(2), 硬軟区分判定表_区分 xml_char(5), 硬軟区分判定表_説明 xml_char(25)
    -> FeatureMerger_B [SUPPLIER]
FeatureMerger_B
    ATTR_ACCUM_MODE = Merge Supplier
    ATTR_CONFLICT_RES = Use Requestor
    GROUP_BY = fme_dataset
    IGNORE_NULLS = No
    JOIN_KEYS = @Value(硬軟区分_硬軟区分) @Value(硬軟区分判定表_コード) AUTO
    MERGE_TYPE = Attributes Only
    PROCESS_DUPS = NO
    REJECT_NULL_MISSING_KEYS = No
    SUPPLIERS_FIRST = No
    MERGED -> AttributeRemover_B
    UNMERGED_REQUESTOR -> AttributeRemover_B
AttributeRemover_B
    REMOVE_ATTRS = xml_matched_element,xml_fragment,ボーリング情報.DTD_version,xml_parent_id,xml_parent_child_pos,硬軟区分_硬軟区分,xml_id
    -> BulkAttributeRenamer_B
BulkAttributeRenamer_B
    ATTRCHOICE = Selected Attributes
    ATTRLIST = 硬軟区分判定表_記号 硬軟区分判定表_コード 硬軟区分判定表_区分 硬軟区分判定表_説明 硬軟区分_下端深度
    MODE_CHOICE = RENAME
    PATTERN_ACTION_DISP = PCREGEXPREPLACE
    REPLACE_PATTERN = ^.+?_(.+)$
    REPLACE_STR = \1
    -> FeatureMerger_B_2 [REQUESTOR]
FeatureMerger_B_2
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_B
BulkAttributeTrimmerArcGISProVer_B
    -> 3DForcer_B
3DForcer_B
    KEEPZVAL = No
    ZVALATTR = @Value(孔口標高)-@Value(下端深度)
    -> コア情報_硬軟区分 (writer GEODATABASE_FILE_1)
コア情報_硬軟区分 (writer GEODATABASE_FILE_1)
    attributes: ボーリングID char(100), DTD_version char(8), 孔口標高 double(8,2), 下端深度 double(8,2), コード char(4), 記号 char(10), 区分 char(20), 説明 char(200)
FeatureMerger_B_7
    ATTR_ACCUM_MODE = Merge Supplier
    ATTR_CONFLICT_RES = Use Requestor
    GROUP_BY = fme_dataset
    IGNORE_NULLS = No
    JOIN_KEYS = @Value(割れ目の状態区分_割れ目の状態区分) @Value(割れ目の状態区分判定表_コード) AUTO
    MERGE_TYPE = Attributes Only
    PROCESS_DUPS = NO
    REJECT_NULL_MISSING_KEYS = No
    SUPPLIERS_FIRST = No
    MERGED -> BulkAttributeRenamer_B_3
    UNMERGED_REQUESTOR -> BulkAttributeRenamer_B_3
BulkAttributeRenamer_B_3
    ATTRCHOICE = Selected Attributes
    ATTRLIST = 割れ目の状態区分_下端深度 割れ目区分_下端深度 割れ目区分判定表_記号 割れ目区分判定表_区分 割れ目区分_割れ目区分 割れ目の状態区分判定表_記号 割れ目区分判定表_説明 割れ目の状態区分_割れ目の状態区分 割れ目の状態区分判定表_区分 割れ目区分判定表_コード 割れ目の状態区分判定表_コード 割れ目の状態区分判定表_説明
    MODE_CHOICE = RENAME
    PATTERN_ACTION_DISP = PCREGEXPREPLACE
    REPLACE_PATTERN = ^.+?_(.+)$
    REPLACE_STR = \1
    -> AttributeRemover_B_3
AttributeRemover_B_3
    REMOVE_ATTRS = xml_parent_id,割れ目の状態区分,xml_fragment,割れ目区分,xml_parent_child_pos,xml_id,ボーリング情報.DTD_version,xml_matched_element
    -> FeatureMerger_B_8 [REQUESTOR]
FeatureMerger_B_8
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_B_3
BulkAttributeTrimmerArcGISProVer_B_3
    -> 3DForcer_B_3
3DForcer_B_3
    KEEPZVAL = No
    ZVALATTR = @Value(孔口標高)-@Value(下端深度)
    -> コア情報_割れ目の状態区分 (writer GEODATABASE_FILE_1)
コア情報_割れ目の状態区分 (writer GEODATABASE_FILE_1)
    attributes: ボーリングID char(100), DTD_version char(8), 孔口標高 double(8,2), 下端深度 double(8,2), コード char(4), 記号 char(10), 区分 char(20), 説明 char(200)
FeatureMerger_B_10
    ATTR_ACCUM_MODE = Merge Supplier
    ATTR_CONFLICT_RES = Use Requestor
    GROUP_BY = fme_dataset
    IGNORE_NULLS = No
    JOIN_KEYS = @Value(風化の程度区分_風化の程度区分) @Value(風化の程度区分判定表_コード) AUTO
    MERGE_TYPE = Attributes Only
    PROCESS_DUPS = NO
    REJECT_NULL_MISSING_KEYS = No
    SUPPLIERS_FIRST = No
    MERGED -> BulkAttributeRenamer_B_4
    UNMERGED_REQUESTOR -> BulkAttributeRenamer_B_4
BulkAttributeRenamer_B_4
    ATTRCHOICE = Selected Attributes
    ATTRLIST = 風化の程度区分判定表_記号 風化区分判定表_コード 風化の程度区分判定表_区分 風化の程度区分_風化の程度区分 風化区分_下端深度 風化の程度区分判定表_コード 風化区分_風化区分 風化の程度区分判定表_説明 風化の程度区分_下端深度 風化区分判定表_説明 風化区分判定表_区分 風化区分判定表_記号
    MODE_CHOICE = RENAME
    PATTERN_ACTION_DISP = PCREGEXPREPLACE
    REPLACE_PATTERN = ^.+?_(.+)$
    REPLACE_STR = \1
    -> AttributeRemover_B_4
AttributeRemover_B_4
    REMOVE_ATTRS = xml_parent_id,xml_fragment,風化区分,xml_parent_child_pos,xml_id,ボーリング情報.DTD_version,xml_matched_element,風化の程度区分
    -> FeatureMerger_B_11 [REQUESTOR]
FeatureMerger_B_11
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_B_4
BulkAttributeTrimmerArcGISProVer_B_4
    -> 3DForcer_B_4
3DForcer_B_4
    KEEPZVAL = No
    ZVALATTR = @Value(孔口標高)-@Value(下端深度)
    -> コア情報_風化の程度区分 (writer GEODATABASE_FILE_1)
コア情報_風化の程度区分 (writer GEODATABASE_FILE_1)
    attributes: ボーリングID char(100), DTD_version char(8), 孔口標高 double(8,2), 下端深度 double(8,2), コード char(4), 記号 char(10), 区分 char(20), 説明 char(200)
FeatureMerger_B_13
    ATTR_ACCUM_MODE = Merge Supplier
    ATTR_CONFLICT_RES = Use Requestor
    GROUP_BY = fme_dataset
    IGNORE_NULLS = No
    JOIN_KEYS = @Value(熱水変質の程度区分_熱水変質の程度区分) @Value(熱水変質の程度区分判定表_コード) AUTO
    MERGE_TYPE = Attributes Only
    PROCESS_DUPS = NO
    REJECT_NULL_MISSING_KEYS = No
    SUPPLIERS_FIRST = No
    MERGED -> BulkAttributeRenamer_B_5
    UNMERGED_REQUESTOR -> BulkAttributeRenamer_B_5
BulkAttributeRenamer_B_5
    ATTRCHOICE = Selected Attributes
    ATTRLIST = 熱水変質の程度区分_下端深度 変質区分判定表_記号 変質区分_下端深度 変質区分判定表_説明 熱水変質の程度区分_熱水変質の程度区分 熱水変質の程度区分判定表_説明 変質区分_変質区分 熱水変質の程度区分判定表_コード 熱水変質の程度区分判定表_記号 変質区分判定表_コード 熱水変質の程度区分判定表_区分 変質区分判定表_区分
    MODE_CHOICE = RENAME
    PATTERN_ACTION_DISP = PCREGEXPREPLACE
    REPLACE_PATTERN = ^.+?_(.+)$
    REPLACE_STR = \1
    -> AttributeRemover_B_5
AttributeRemover_B_5
    REMOVE_ATTRS = xml_fragment,xml_parent_child_pos,xml_matched_element,xml_parent_id,熱水変質の程度区分,xml_id,ボーリング情報.DTD_version,変質区分
    -> FeatureMerger_B_14 [REQUESTOR]
FeatureMerger_B_14
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_B_5
BulkAttributeTrimmerArcGISProVer_B_5
    -> 3DForcer_B_5
3DForcer_B_5
    KEEPZVAL = No
    ZVALATTR = @Value(孔口標高)-@Value(下端深度)
    -> コア情報_熱水変質の程度区分 (writer GEODATABASE_FILE_1)
コア情報_熱水変質の程度区分 (writer GEODATABASE_FILE_1)
    attributes: ボーリングID char(100), DTD_version char(8), 孔口標高 double(8,2), 下端深度 double(8,2), コード char(4), 記号 char(10), 区分 char(20), 説明 char(200)
破砕度 (reader XML_1)
    attributes: xml_fragment xml_xml, xml_id xml_char(18), xml_matched_element xml_char(7), xml_parent_child_pos xml_char(1), xml_parent_id xml_char(1), ボーリング情報.DTD_version xml_decimal(4,2), 破砕度_下端深度 xml_decimal(4,2), 破砕度_上端深度 xml_decimal(4,2), 破砕度_破砕度 xml_decimal(4,0)
    -> FeatureMerger_B_15 [REQUESTOR]
FeatureMerger_B_15
    ATTR_ACCUM_MODE = Merge Supplier
    ATTR_CONFLICT_RES = Use Requestor
    GROUP_BY = fme_dataset
    IGNORE_NULLS = No
    JOIN_KEYS = @Value(破砕度_破砕度) @Value(破砕度判定表_コード) AUTO
    MERGE_TYPE = Attributes Only
    PROCESS_DUPS = NO
    REJECT_NULL_MISSING_KEYS = No
    SUPPLIERS_FIRST = No
    MERGED -> BulkAttributeRenamer_B_7
    UNMERGED_REQUESTOR -> BulkAttributeRenamer_B_7
BulkAttributeRenamer_B_7
    ATTRCHOICE = All Attributes
    MODE_CHOICE = RENAME
    PATTERN_ACTION_DISP = PCREGEXPREPLACE
    REPLACE_PATTERN = ^破砕度.*?_(.+)$
    REPLACE_STR = \1
    -> AttributeRemover_B_7
AttributeRemover_B_7
    LIST_ATTRS = _table{}.desc _table{}.item
    REMOVE_ATTRS = 破砕度,xml_fragment,xml_matched_element,xml_parent_id,xml_id,ボーリング情報.DTD_version,xml_parent_child_pos
    -> FeatureMerger_B_16 [REQUESTOR]
FeatureMerger_B_16
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> AttributeManager_2
AttributeManager_2
    ATTR_TABLE:
      SET_TO 説明_説明 = @Value(説明{0}.説明)
      SET_TO 説明_項目名 = @Value(説明{0}.項目名)
    -> BulkAttributeTrimmerArcGISProVer_B_6
BulkAttributeTrimmerArcGISProVer_B_6
    -> 3DForcer_B_6
3DForcer_B_6
    KEEPZVAL = No
    ZVALATTR = @Value(孔口標高)-@Value(下端深度)
    -> コア情報_破砕度 (writer GEODATABASE_FILE_1)
コア情報_破砕度 (writer GEODATABASE_FILE_1)
    attributes: ボーリングID char(100), DTD_version char(8), 孔口標高 double(8,2), 上端深度 double(8,2), 下端深度 double(8,2), コード char(4), 記号 char(10), 説明_項目名 char(2048), 説明_説明 char(2048)
岩級区分 (reader XML_1)
    attributes: xml_fragment xml_xml, xml_id xml_char(20), xml_matched_element xml_char(9), xml_parent_child_pos xml_char(1), xml_parent_id xml_char(1), ボーリング情報.DTD_version xml_decimal(4,2), 岩級区分_下端深度 xml_decimal(5,2), 岩級区分_岩級区分 xml_decimal(4,0)
    -> FeatureMerger_B_17 [REQUESTOR]
FeatureMerger_B_17
    ATTR_ACCUM_MODE = Merge Supplier
    ATTR_CONFLICT_RES = Use Requestor
    GROUP_BY = fme_dataset
    IGNORE_NULLS = No
    JOIN_KEYS = @Value(岩級区分_岩級区分) @Value(岩級区分判定表_コード) AUTO
    MERGE_TYPE = Attributes Only
    PROCESS_DUPS = NO
    REJECT_NULL_MISSING_KEYS = No
    SUPPLIERS_FIRST = No
    MERGED -> BulkAttributeRenamer_B_9
    UNMERGED_REQUESTOR -> BulkAttributeRenamer_B_9
BulkAttributeRenamer_B_9
    ATTRCHOICE = All Attributes
    MODE_CHOICE = RENAME
    PATTERN_ACTION_DISP = PCREGEXPREPLACE
    REPLACE_PATTERN = ^岩級区分.*?_(.+)$
    REPLACE_STR = \1
    -> AttributeRemover_B_9
AttributeRemover_B_9
    LIST_ATTRS = _table{}.desc _table{}.item
    REMOVE_ATTRS = xml_fragment,xml_matched_element,xml_parent_id,岩級区分,xml_id,ボーリング情報.DTD_version,xml_parent_child_pos
    -> FeatureMerger_B_18 [REQUESTOR]
FeatureMerger_B_18
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> AttributeManager_3
AttributeManager_3
    ATTR_TABLE:
      SET_TO 説明_説明 = @Value(説明{0}.説明)
      SET_TO 説明_項目名 = @Value(説明{0}.項目名)
    -> BulkAttributeTrimmerArcGISProVer_B_7
BulkAttributeTrimmerArcGISProVer_B_7
    -> 3DForcer_B_7
3DForcer_B_7
    KEEPZVAL = No
    ZVALATTR = @Value(孔口標高)-@Value(下端深度)
    -> コア情報_岩級区分 (writer GEODATABASE_FILE_1)
コア情報_岩級区分 (writer GEODATABASE_FILE_1)
    attributes: ボーリングID char(100), DTD_version char(8), 孔口標高 double(8,2), 下端深度 double(8,2), コード char(4), 記号 char(10), 説明_項目名 char(2048), 説明_説明 char(2048)
色調 (reader XML_1)
    attributes: xml_fragment xml_xml, xml_id xml_char(15), xml_matched_element xml_char(5), xml_parent_child_pos xml_char(1), xml_parent_id xml_char(1), ボーリング情報.DTD_version xml_decimal(4,2), 色調_下端深度 xml_decimal(5,2), 色調_色調名 xml_char(7)
    -> AttributeRemover_A
AttributeRemover_A
    REMOVE_ATTRS = xml_matched_element,xml_fragment,ボーリング情報.DTD_version,xml_parent_id,xml_parent_child_pos,xml_id
    -> BulkAttributeRenamer_A
BulkAttributeRenamer_A
    ATTRCHOICE = Selected Attributes
    ATTRLIST = 色調_色調名 色調_下端深度
    CASE_DISP = YES
    MODE_CHOICE = RENAME
    PATTERN_ACTION_DISP = REMOVEPREFIX
    REPLACE_STR = 色調_
    -> FeatureMerger_A [REQUESTOR]
FeatureMerger_A
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_A
BulkAttributeTrimmerArcGISProVer_A
    -> 3DForcer_A
3DForcer_A
    KEEPZVAL = No
    ZVALATTR = @Value(孔口標高)-@Value(下端深度)
    -> コア情報_色調 (writer GEODATABASE_FILE_1)
コア情報_色調 (writer GEODATABASE_FILE_1)
    attributes: ボーリングID char(100), DTD_version char(8), 孔口標高 double(8,2), 下端深度 double(8,2), 色調名 char(20)
観察記事 (reader XML_1)
    attributes: xml_fragment xml_xml, xml_id xml_char(19), xml_matched_element xml_char(9), xml_parent_child_pos xml_char(1), xml_parent_id xml_char(1), ボーリング情報.DTD_version xml_decimal(4,2), 観察記事_下端深度 xml_decimal(5,2), 観察記事_記事 xml_char(47), 観察記事_上端深度 xml_decimal(5,2)
    -> AttributeRemover_A_2
AttributeRemover_A_2
    REMOVE_ATTRS = xml_matched_element,xml_fragment,ボーリング情報.DTD_version,xml_parent_id,xml_parent_child_pos,xml_id
    -> BulkAttributeRenamer_A_2
BulkAttributeRenamer_A_2
    ATTRCHOICE = Selected Attributes
    ATTRLIST = 観察記事_上端深度 観察記事_記事 観察記事_下端深度
    CASE_DISP = YES
    MODE_CHOICE = RENAME
    PATTERN_ACTION_DISP = REMOVEPREFIX
    REPLACE_STR = 観察記事_
    -> FeatureMerger_A_2 [REQUESTOR]
FeatureMerger_A_2
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_A_2
BulkAttributeTrimmerArcGISProVer_A_2
    -> 3DForcer_A_2
3DForcer_A_2
    KEEPZVAL = No
    ZVALATTR = @Value(孔口標高)-@Value(下端深度)
    -> コア情報_観察記事 (writer GEODATABASE_FILE_1)
コア情報_観察記事 (writer GEODATABASE_FILE_1)
    attributes: ボーリングID char(100), DTD_version char(8), 孔口標高 double(8,2), 上端深度 double(8,2), 下端深度 double(8,2), 記事 char(200)
観察記事枠線 (reader XML_1)
    attributes: xml_fragment xml_xml, xml_id xml_char(23), xml_matched_element xml_char(13), xml_parent_child_pos xml_char(1), xml_parent_id xml_char(1), ボーリング情報.DTD_version xml_decimal(4,2), 観察記事枠線_下端深度 xml_decimal(5,2)
    -> AttributeRemover_A_3
AttributeRemover_A_3
    REMOVE_ATTRS = xml_fragment,xml_parent_child_pos,xml_matched_element,xml_parent_id,xml_id,ボーリング情報.DTD_version
    -> AttributeRenamer_A
AttributeRenamer_A
    ATTR_TABLE = RENAME_SET_DEFAULT 観察記事枠線_下端深度 > 下端深度
    MISSING_INPUT_ATTRS = PRESERVE
    -> FeatureMerger_A_3 [REQUESTOR]
FeatureMerger_A_3
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_A_3
BulkAttributeTrimmerArcGISProVer_A_3
    -> 3DForcer_A_3
3DForcer_A_3
    KEEPZVAL = No
    ZVALATTR = @Value(孔口標高)-@Value(下端深度)
    -> コア情報_観察記事枠線 (writer GEODATABASE_FILE_1)
コア情報_観察記事枠線 (writer GEODATABASE_FILE_1)
    attributes: ボーリングID char(100), DTD_version char(8), 孔口標高 double(8,2), 下端深度 double(8,2)
相対密度稠度 (reader XML_1)
    attributes: xml_fragment xml_xml, xml_id xml_char(23), xml_matched_element xml_char(13), xml_parent_child_pos xml_char(1), xml_parent_id xml_char(1), ボーリング情報.DTD_version xml_decimal(4,2), 相対密度_コード xml_char(255), 相対密度_状態 xml_char(9), 相対密度稠度_下端深度 xml_decimal(5,2), 相対稠度_コード xml_char(255), 相対稠度_状態 xml_char(9)
    -> AttributeRenamer_A_3
AttributeRenamer_A_3
    ATTR_TABLE = RENAME_SET_DEFAULT 相対密度稠度_下端深度 > 下端深度
    MISSING_INPUT_ATTRS = PRESERVE
    -> AttributeRemover_A_8
AttributeRemover_A_8
    REMOVE_ATTRS = xml_parent_id,xml_fragment,xml_id,ボーリング情報.DTD_version,xml_parent_child_pos,xml_matched_element
    -> FeatureMerger_A_9 [REQUESTOR]
FeatureMerger_A_9
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_A_8
BulkAttributeTrimmerArcGISProVer_A_8
    -> 3DForcer_A_8
3DForcer_A_8
    KEEPZVAL = No
    ZVALATTR = @Value(孔口標高)-@Value(下端深度)
    -> コア情報_相対密度稠度 (writer GEODATABASE_FILE_1)
コア情報_相対密度稠度 (writer GEODATABASE_FILE_1)
    attributes: ボーリングID char(100), DTD_version char(8), 孔口標高 double(8,2), 下端深度 double(8,2), 相対密度_コード char(4), 相対密度_状態 char(100), 相対稠度_コード char(4), 相対稠度_状態 char(100)
Note: DTD version 2.10, 3.00
孔内水平載荷試験 (reader XML_1)
    attributes: xml_fragment xml_xml, xml_id xml_char(28), xml_matched_element xml_char(17), xml_parent_child_pos xml_char(1), xml_parent_id xml_char(1), ボーリング情報.DTD_version xml_decimal(4,2), 孔内水平載荷試験_割線弾性係数 xml_decimal(31,15), 孔内水平載荷試験_降伏圧 xml_decimal(6,1), 孔内水平載荷試験_載荷パターン xml_char(13), 孔内水平載荷試験_試験深度 xml_decimal(5,2), 孔内水平載荷試験_試験方法 xml_char(1), 孔内水平載荷試験_試験方法コード xml_decimal(3,0), 孔内水平載荷試験_初期圧 xml_decimal(5,1), 孔内水平載荷試験_接線弾性係数 xml_decimal(31,15), 孔内水平載荷試験_変形係数 xml_decimal(31,15)
    -> AttributeRemover_C
Note: DTD version 4.00
孔内載荷試験 (reader XML_1)
    attributes: xml_fragment xml_xml, xml_id xml_char(24), xml_matched_element xml_char(13), xml_parent_child_pos xml_char(1), xml_parent_id xml_char(1), ボーリング情報.DTD_version xml_decimal(4,2), 孔内載荷試験_割線弾性係数 xml_decimal(31,15), 孔内載荷試験_降伏圧 xml_decimal(6,1), 孔内載荷試験_載荷パターン xml_char(13), 孔内載荷試験_試験深度 xml_decimal(5,2), 孔内載荷試験_試験方法 xml_char(1), 孔内載荷試験_試験方法コード xml_decimal(3,0), 孔内載荷試験_初期圧 xml_decimal(5,1), 孔内載荷試験_接線弾性係数 xml_decimal(31,15), 孔内載荷試験_変形係数 xml_decimal(31,15)
    -> AttributeRemover_C
AttributeRemover_C
    REMOVE_ATTRS = xml_matched_element,xml_fragment,ボーリング情報.DTD_version,xml_parent_id,xml_parent_child_pos,xml_id
    -> BulkAttributeRenamer_C
BulkAttributeRenamer_C
    ATTRCHOICE = Selected Attributes
    ATTRLIST = 孔内水平載荷試験_変形係数 孔内載荷試験_変形係数 孔内載荷試験_試験深度 孔内水平載荷試験_載荷パターン 孔内水平載荷試験_初期圧 孔内水平載荷試験_接線弾性係数 孔内水平載荷試験_試験深度 孔内水平載荷試験_試験方法コード 孔内載荷試験_接線弾性係数 孔内水平載荷試験_降伏圧 孔内載荷試験_降伏圧 孔内載荷試験_試験方法コード 孔内水平載荷試験_試験方法 孔内載荷試験_初期圧 孔内載荷試験_割線弾性係数 孔内載荷試験_試験方法 孔内載荷試験_載荷パターン 孔内水平載荷試験_割線弾性係数
    MODE_CHOICE = RENAME
    PATTERN_ACTION_DISP = PCREGEXPREPLACE
    REPLACE_PATTERN = ^.+?_(.+)$
    REPLACE_STR = \1
    -> FeatureMerger_C [REQUESTOR]
FeatureMerger_C
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_C
BulkAttributeTrimmerArcGISProVer_C
    -> 3DForcer_C
3DForcer_C
    KEEPZVAL = No
    ZVALATTR = @Value(孔口標高)-@Value(試験深度)
    -> ExpressionEvaluator_C
Note: 指数表記文字列 --> 数値 / ・変形係数 / ・割線弾性係数 / ・接線弾性係数
ExpressionEvaluator_C
    ACTION = Overwrite Existing Attributes
    ATTRLIST = 接線弾性係数 変形係数 割線弾性係数
    EXPRESSION = @double(@CurrentAttribute())
    -> コア情報_孔内載荷試験 (writer GEODATABASE_FILE_1)
コア情報_孔内載荷試験 (writer GEODATABASE_FILE_1)
    attributes: ボーリングID char(100), DTD_version char(8), 試験深度 double(8,2), 孔口標高 double(8,2), 試験方法コード char(4), 試験方法 char(100), 載荷パターン char(20), 初期圧 double(8,1), 降伏圧 double(8,1), 変形係数 double, 割線弾性係数 double, 接線弾性係数 double
透水試験 (reader XML_1)
    attributes: xml_fragment xml_xml, xml_id xml_char(20), xml_matched_element xml_char(9), xml_parent_child_pos xml_char(1), xml_parent_id xml_char(1), ボーリング情報.DTD_version xml_decimal(4,2), 透水試験_下端深度 xml_decimal(5,2), 透水試験_試験コード xml_decimal(3,0), 透水試験_試験方法 xml_char(1), 透水試験_上端深度 xml_decimal(5,2), 透水試験_透水係数 xml_decimal(31,15)
    -> AttributeRemover_C_2
AttributeRemover_C_2
    REMOVE_ATTRS = xml_id,xml_matched_element,xml_parent_id,xml_parent_child_pos,ボーリング情報.DTD_version,xml_fragment
    -> BulkAttributeRenamer_C_2
BulkAttributeRenamer_C_2
    ATTRCHOICE = Selected Attributes
    ATTRLIST = 透水試験_下端深度 透水試験_透水係数 透水試験_上端深度 透水試験_試験方法 透水試験_試験コード
    CASE_DISP = YES
    MODE_CHOICE = RENAME
    PATTERN_ACTION_DISP = REMOVEPREFIX
    REPLACE_STR = 透水試験_
    -> FeatureMerger_C_2 [REQUESTOR]
FeatureMerger_C_2
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_C_2
BulkAttributeTrimmerArcGISProVer_C_2
    -> 3DForcer_C_2
3DForcer_C_2
    KEEPZVAL = No
    ZVALATTR = @Value(孔口標高)-@Value(下端深度)
    -> AttributeRenamer_C
Note: AttributeRenamer_C [AttributeRenamer] / Attributes To Rename: Input AttributeOutput AttributeDefault Value試験コード試験方法コード If Input Attribute Is Missing: Preserve Existing Output Attribute
AttributeRenamer_C
    ATTR_TABLE = RENAME_SET_DEFAULT 試験コード > 試験方法コード
    MISSING_INPUT_ATTRS = PRESERVE
    -> ExpressionEvaluator_C_2
Note: 指数表示文字列 --> 数値 / ・透水係数
ExpressionEvaluator_C_2
    ACTION = Overwrite Existing Attributes
    ATTRLIST = 透水係数
    EXPRESSION = @double(@CurrentAttribute())
    -> コア情報_透水試験 (writer GEODATABASE_FILE_1)
コア情報_透水試験 (writer GEODATABASE_FILE_1)
    attributes: ボーリングID char(100), DTD_version char(8), 孔口標高 double(8,2), 上端深度 double(8,2), 下端深度 double(8,2), 試験方法コード char(4), 試験方法 char(100), 透水係数 double
P波試験 (reader XML_1)
    attributes: P波試験_下端深度 xml_decimal(5,2), P波試験_起振方式 xml_char(19), P波試験_上端深度 xml_decimal(4,2), P波試験_速度 xml_decimal(4,0), xml_fragment xml_xml, xml_id xml_char(19), xml_matched_element xml_char(8), xml_parent_child_pos xml_char(1), xml_parent_id xml_char(1), ボーリング情報.DTD_version xml_decimal(4,2)
    -> AttributeRemover_C_3
AttributeRemover_C_3
    REMOVE_ATTRS = xml_id,xml_matched_element,xml_parent_id,xml_parent_child_pos,ボーリング情報.DTD_version,xml_fragment
    -> BulkAttributeRenamer_C_3
BulkAttributeRenamer_C_3
    ATTRCHOICE = Selected Attributes
    ATTRLIST = P波試験_上端深度 P波試験_起振方式 P波試験_速度 P波試験_下端深度
    CASE_DISP = YES
    MODE_CHOICE = RENAME
    PATTERN_ACTION_DISP = REMOVEPREFIX
    REPLACE_STR = P波試験_
    -> FeatureMerger_C_3 [REQUESTOR]
FeatureMerger_C_3
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_C_3
BulkAttributeTrimmerArcGISProVer_C_3
    -> 3DForcer_C_3
3DForcer_C_3
    KEEPZVAL = No
    ZVALATTR = @Value(孔口標高)-@Value(下端深度)
    -> コア情報_P波試験 (writer GEODATABASE_FILE_1)
コア情報_P波試験 (writer GEODATABASE_FILE_1)
    attributes: ボーリングID char(100), DTD_version char(8), 孔口標高 double(8,2), 上端深度 double(8,2), 下端深度 double(8,2), 起振方式 char(40), 速度 integer
S波試験 (reader XML_1)
    attributes: S波試験_下端深度 xml_decimal(5,2), S波試験_起振方式 xml_char(9), S波試験_上端深度 xml_decimal(4,2), S波試験_速度 xml_decimal(4,0), xml_fragment xml_xml, xml_id xml_char(19), xml_matched_element xml_char(8), xml_parent_child_pos xml_char(1), xml_parent_id xml_char(1), ボーリング情報.DTD_version xml_decimal(4,2)
    -> AttributeRemover_C_4
AttributeRemover_C_4
    REMOVE_ATTRS = xml_id,xml_matched_element,xml_parent_id,xml_parent_child_pos,ボーリング情報.DTD_version,xml_fragment
    -> BulkAttributeRenamer_C_4
BulkAttributeRenamer_C_4
    ATTRCHOICE = Selected Attributes
    ATTRLIST = S波試験_速度 S波試験_下端深度 S波試験_起振方式 S波試験_上端深度
    CASE_DISP = YES
    MODE_CHOICE = RENAME
    PATTERN_ACTION_DISP = REMOVEPREFIX
    REPLACE_STR = S波試験_
    -> FeatureMerger_C_4 [REQUESTOR]
FeatureMerger_C_4
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_C_4
BulkAttributeTrimmerArcGISProVer_C_4
    -> 3DForcer_C_4
3DForcer_C_4
    KEEPZVAL = No
    ZVALATTR = @Value(孔口標高)-@Value(下端深度)
    -> コア情報_S波試験 (writer GEODATABASE_FILE_1)
コア情報_S波試験 (writer GEODATABASE_FILE_1)
    attributes: ボーリングID char(100), DTD_version char(8), 孔口標高 double(8,2), 上端深度 double(8,2), 下端深度 double(8,2), 起振方式 char(40), 速度 integer
その他原位置試験 (reader XML_1)
    attributes: xml_fragment xml_xml, xml_id xml_char(28), xml_matched_element xml_char(17), xml_parent_child_pos xml_char(1), xml_parent_id xml_char(1), その他原位置試験_下端深度 xml_decimal(5,2), その他原位置試験_試験結果 xml_char(10), その他原位置試験_試験名 xml_char(23), その他原位置試験_上端深度 xml_decimal(5,2), ボーリング情報.DTD_version xml_decimal(4,2)
    -> AttributeRemover_C_5
AttributeRemover_C_5
    REMOVE_ATTRS = xml_id,xml_matched_element,xml_parent_id,xml_parent_child_pos,ボーリング情報.DTD_version,xml_fragment
    -> BulkAttributeRenamer_C_5
BulkAttributeRenamer_C_5
    ATTRCHOICE = Selected Attributes
    ATTRLIST = その他原位置試験_試験名 その他原位置試験_上端深度 その他原位置試験_下端深度 その他原位置試験_試験結果
    CASE_DISP = YES
    MODE_CHOICE = RENAME
    PATTERN_ACTION_DISP = REMOVEPREFIX
    REPLACE_STR = その他原位置試験_
    -> FeatureMerger_C_5 [REQUESTOR]
FeatureMerger_C_5
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_C_5
BulkAttributeTrimmerArcGISProVer_C_5
    -> 3DForcer_C_5
3DForcer_C_5
    KEEPZVAL = No
    ZVALATTR = @Value(孔口標高)-@Value(下端深度)
    -> コア情報_その他原位置試験 (writer GEODATABASE_FILE_1)
コア情報_その他原位置試験 (writer GEODATABASE_FILE_1)
    attributes: ボーリングID char(100), DTD_version char(8), 孔口標高 double(8,2), 試験名 char(40), 上端深度 double(8,2), 下端深度 double(8,2), 試験結果 char(200)
試料採取 (reader XML_1)
    attributes: xml_fragment xml_xml, xml_id xml_char(20), xml_matched_element xml_char(9), xml_parent_child_pos xml_char(1), xml_parent_id xml_char(1), ボーリング情報.DTD_version xml_decimal(4,2), 試料採取_下端深度 xml_decimal(5,2), 試料採取_採取方法 xml_char(13), 試料採取_採取方法コード xml_decimal(4,0), 試料採取_試験名{} xml_char(255), 試料採取_試料番号 xml_char(5), 試料採取_上端深度 xml_decimal(5,2)
    -> AttributeRemover_C_6
AttributeRemover_C_6
    REMOVE_ATTRS = xml_id,xml_matched_element,xml_parent_id,xml_parent_child_pos,ボーリング情報.DTD_version,xml_fragment
    -> BulkAttributeRenamer_C_6
BulkAttributeRenamer_C_6
    ATTRCHOICE = Selected Attributes
    ATTRLIST = 試料採取_上端深度 試料採取_採取方法コード 試料採取_採取方法 試料採取_下端深度 試料採取_試料番号
    CASE_DISP = YES
    MODE_CHOICE = RENAME
    PATTERN_ACTION_DISP = REMOVEPREFIX
    REPLACE_STR = 試料採取_
    -> ListRenamer_C
ListRenamer_C
    LEAVE_ORIG = No
    LIST_ACTION = Rename
    LIST_COMPONENT_NAMES = 試料採取_試験名{},試験名{}
    LIST_NAME = 試料採取_試験名{}
    -> FeatureMerger_C_6 [REQUESTOR]
FeatureMerger_C_6
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> AttributeManager_4
AttributeManager_4
    ATTR_TABLE = SET_TO 試験名 = @Value(試験名{0})
    -> BulkAttributeTrimmerArcGISProVer_C_6
BulkAttributeTrimmerArcGISProVer_C_6
    -> 3DForcer_C_6
3DForcer_C_6
    KEEPZVAL = No
    ZVALATTR = @Value(孔口標高)-@Value(下端深度)
    -> コア情報_試料採取 (writer GEODATABASE_FILE_1)
コア情報_試料採取 (writer GEODATABASE_FILE_1)
    attributes: ボーリングID char(100), DTD_version char(8), 孔口標高 double(8,2), 上端深度 double(8,2), 下端深度 double(8,2), 試料番号 char(20), 採取方法コード char(4), 採取方法 char(100), 試験名 char(2048)
地盤材料の工学的分類 (reader XML_1)
    attributes: xml_fragment xml_xml, xml_id xml_char(32), xml_matched_element xml_char(21), xml_parent_child_pos xml_char(1), xml_parent_id xml_char(1), ボーリング情報.DTD_version xml_decimal(4,2), 地盤分類_下端深度 xml_decimal(5,2), 地盤分類_工学的分類記号 xml_char(3)
    -> AttributeRemover_C_7
AttributeRemover_C_7
    REMOVE_ATTRS = xml_id,xml_matched_element,xml_parent_id,xml_parent_child_pos,ボーリング情報.DTD_version,xml_fragment
    -> BulkAttributeRenamer_C_7
BulkAttributeRenamer_C_7
    ATTRCHOICE = Selected Attributes
    ATTRLIST = 地盤分類_工学的分類記号 地盤分類_下端深度
    CASE_DISP = YES
    MODE_CHOICE = RENAME
    PATTERN_ACTION_DISP = REMOVEPREFIX
    REPLACE_STR = 地盤分類_
    -> FeatureMerger_C_7 [REQUESTOR]
FeatureMerger_C_7
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_C_7
BulkAttributeTrimmerArcGISProVer_C_7
    -> 3DForcer_C_7
3DForcer_C_7
    KEEPZVAL = No
    ZVALATTR = @Value(孔口標高)-@Value(下端深度)
    -> コア情報_地盤材料の工学的分類 (writer GEODATABASE_FILE_1)
コア情報_地盤材料の工学的分類 (writer GEODATABASE_FILE_1)
    attributes: ボーリングID char(100), DTD_version char(8), 孔口標高 double(8,2), 下端深度 double(8,2), 工学的分類記号 char(10)
地質時代 (reader XML_1)
    attributes: xml_fragment xml_xml, xml_id xml_char(20), xml_matched_element xml_char(9), xml_parent_child_pos xml_char(1), xml_parent_id xml_char(1), ボーリング情報.DTD_version xml_decimal(4,2), 地質時代_コード xml_decimal(6,0), 地質時代_下端深度 xml_decimal(5,2), 地質時代_時代名 xml_char(13), 地質時代_上端深度 xml_decimal(5,2), 地質時代_形成年代下限 xml_decimal(10,0), 地質時代_地質時代名 xml_char(13), 地質時代_変成年代下限 xml_char(1), 地質時代_形成年代上限 xml_decimal(10,0), 地質時代_変成年代上限 xml_char(1)
    -> AttributeRemover_C_8
AttributeRemover_C_8
    REMOVE_ATTRS = xml_id,xml_matched_element,xml_parent_id,xml_parent_child_pos,ボーリング情報.DTD_version,xml_fragment
    -> BulkAttributeRenamer_C_8
BulkAttributeRenamer_C_8
    ATTRCHOICE = Selected Attributes
    ATTRLIST = 地質時代_時代名 地質時代_上端深度 地質時代_形成年代上限 地質時代_地質時代名 地質時代_形成年代下限 地質時代_コード 地質時代_変成年代下限 地質時代_変成年代上限 地質時代_下端深度
    CASE_DISP = YES
    MODE_CHOICE = RENAME
    PATTERN_ACTION_DISP = REMOVEPREFIX
    REPLACE_STR = 地質時代_
    -> AttributeRenamer_C_2
AttributeRenamer_C_2
    ATTR_TABLE:
      RENAME_SET_DEFAULT コード > 地質時代コード
      RENAME_SET_DEFAULT 時代名 > 地質時代名
    MISSING_INPUT_ATTRS = PRESERVE
    -> FeatureMerger_C_8 [REQUESTOR]
FeatureMerger_C_8
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_C_8
BulkAttributeTrimmerArcGISProVer_C_8
    -> 3DForcer_C_8
3DForcer_C_8
    KEEPZVAL = No
    ZVALATTR = @Value(孔口標高)-@Value(下端深度)
    -> コア情報_地質時代 (writer GEODATABASE_FILE_1)
コア情報_地質時代 (writer GEODATABASE_FILE_1)
    attributes: ボーリングID char(100), DTD_version char(8), 孔口標高 double(8,2), 上端深度 double(8,2), 下端深度 double(8,2), 地質時代コード char(6), 地質時代名 char(100), 形成年代上限 char(10), 形成年代下限 char(10), 変成年代上限 char(10), 変成年代下限 char(10)
地層岩体区分 (reader XML_1)
    attributes: xml_fragment xml_xml, xml_id xml_char(24), xml_matched_element xml_char(13), xml_parent_child_pos xml_char(1), xml_parent_id xml_char(1), ボーリング情報.DTD_version xml_decimal(4,2), 地層岩体区分_下端深度 xml_decimal(5,2), 地層岩体区分_上端深度 xml_decimal(5,2), 地層岩体区分_地層岩体名 xml_char(9)
    -> AttributeRemover_C_9
AttributeRemover_C_9
    REMOVE_ATTRS = xml_id,xml_matched_element,xml_parent_id,xml_parent_child_pos,ボーリング情報.DTD_version,xml_fragment
    -> BulkAttributeRenamer_C_9
BulkAttributeRenamer_C_9
    ATTRCHOICE = Selected Attributes
    ATTRLIST = 地層岩体区分_上端深度 地層岩体区分_下端深度 地層岩体区分_地層岩体名
    CASE_DISP = YES
    MODE_CHOICE = RENAME
    PATTERN_ACTION_DISP = REMOVEPREFIX
    REPLACE_STR = 地層岩体区分_
    -> FeatureMerger_C_9 [REQUESTOR]
FeatureMerger_C_9
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_C_9
BulkAttributeTrimmerArcGISProVer_C_9
    -> 3DForcer_C_9
3DForcer_C_9
    KEEPZVAL = No
    ZVALATTR = @Value(孔口標高)-@Value(下端深度)
    -> コア情報_地層岩体区分 (writer GEODATABASE_FILE_1)
コア情報_地層岩体区分 (writer GEODATABASE_FILE_1)
    attributes: ボーリングID char(100), DTD_version char(8), 孔口標高 double(8,2), 上端深度 double(8,2), 下端深度 double(8,2), 地層岩体名 char(100)
孔内水位 (reader XML_1)
    attributes: xml_fragment xml_xml, xml_id xml_char(20), xml_matched_element xml_char(9), xml_parent_child_pos xml_char(1), xml_parent_id xml_char(1), ボーリング情報.DTD_version xml_decimal(4,2), 孔内水位_掘削状況 xml_char(1), 孔内水位_掘削状況コード xml_decimal(2,0), 孔内水位_孔内水位 xml_char(5), 孔内水位_水位種別コード xml_decimal(3,0), 孔内水位_水位種別備考 xml_char(255), 孔内水位_測定年月日 xml_char(11), 孔内水位_削孔状況 xml_decimal(2,0), 孔内水位_削孔状況コード xml_decimal(2,0)
    -> AttributeRemover_D
AttributeRemover_D
    REMOVE_ATTRS = xml_id,xml_matched_element,xml_parent_id,xml_parent_child_pos,ボーリング情報.DTD_version,xml_fragment
    -> BulkAttributeRenamer_D
BulkAttributeRenamer_D
    ATTRCHOICE = Selected Attributes
    ATTRLIST = 孔内水位_掘削状況コード 孔内水位_水位種別コード 孔内水位_掘削状況 孔内水位_孔内水位 孔内水位_削孔状況コード 孔内水位_削孔状況 孔内水位_測定年月日 孔内水位_水位種別備考
    CASE_DISP = YES
    MODE_CHOICE = RENAME
    PATTERN_ACTION_DISP = REMOVEPREFIX
    REPLACE_STR = 孔内水位_
    -> AttributeRenamer_D
AttributeRenamer_D
    ATTR_TABLE:
      RENAME_SET_DEFAULT 掘削状況 > 削孔状況
      RENAME_SET_DEFAULT 掘削状況コード > 削孔状況コード
    MISSING_INPUT_ATTRS = PRESERVE
    -> DateFormatter_D
DateFormatter_D
    DATE_ATTR = 測定年月日
    FMT = FME Date/Time (%Y%m%d%H%M%S)
    SRCFMT = %Y-%m-%d
    -> FeatureMerger_D [REQUESTOR]
FeatureMerger_D
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_D
BulkAttributeTrimmerArcGISProVer_D
    -> 2DForcer_D
Note: 2Dポイント
2DForcer_D
    2D -> コア情報_孔内水位 (writer GEODATABASE_FILE_1)
コア情報_孔内水位 (writer GEODATABASE_FILE_1)
    attributes: ボーリングID char(100), DTD_version char(8), 孔口標高 double(8,2), 測定年月日 date, 削孔状況コード char(2), 削孔状況 char(100), 孔内水位 double(8,2), 水位種別コード char(4), 水位種別備考 char(100)
Note: DTD version 2.10
掘削工程 (reader XML_1)
    attributes: xml_fragment xml_xml, xml_id xml_char(20), xml_matched_element xml_char(9), xml_parent_child_pos xml_char(1), xml_parent_id xml_char(1), ボーリング情報.DTD_version xml_decimal(4,2), 掘削工程_ケーシング下端深度 xml_decimal(5,2), 掘削工程_掘進深度 xml_decimal(5,2), 掘削工程_測定年月日 xml_char(11)
    -> AttributeRemover_D_2
Note: DTD version 3.00, 4.00
削孔工程 (reader XML_1)
    attributes: xml_fragment xml_xml, xml_id xml_char(20), xml_matched_element xml_char(9), xml_parent_child_pos xml_char(1), xml_parent_id xml_char(1), ボーリング情報.DTD_version xml_decimal(4,2), 削孔工程_ケーシング下端深度 xml_decimal(5,2), 削孔工程_削孔深度 xml_decimal(5,2), 削孔工程_測定年月日 xml_char(11)
    -> AttributeRemover_D_2
AttributeRemover_D_2
    REMOVE_ATTRS = xml_id,xml_matched_element,xml_parent_id,xml_parent_child_pos,ボーリング情報.DTD_version,xml_fragment
    -> BulkAttributeRenamer_D_2
BulkAttributeRenamer_D_2
    ATTRCHOICE = Selected Attributes
    ATTRLIST = 削孔工程_削孔深度 削孔工程_ケーシング下端深度 掘削工程_ケーシング下端深度 削孔工程_測定年月日 掘削工程_掘進深度 掘削工程_測定年月日
    MODE_CHOICE = RENAME
    PATTERN_ACTION_DISP = PCREGEXPREPLACE
    REPLACE_PATTERN = ^.+?_(.+)$
    REPLACE_STR = \1
    -> AttributeRenamer_D_2
AttributeRenamer_D_2
    ATTR_TABLE = RENAME_SET_DEFAULT 掘進深度 > 削孔深度
    MISSING_INPUT_ATTRS = PRESERVE
    -> DateFormatter_D_2
DateFormatter_D_2
    DATE_ATTR = 測定年月日
    FMT = FME Date/Time (%Y%m%d%H%M%S)
    SRCFMT = %Y-%m-%d
    -> FeatureMerger_D_2 [REQUESTOR]
FeatureMerger_D_2
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_D_2
BulkAttributeTrimmerArcGISProVer_D_2
    -> 3DForcer_D
3DForcer_D
    KEEPZVAL = No
    ZVALATTR = @Value(孔口標高)-@Value(ケーシング下端深度)
    -> コア情報_削孔工程 (writer GEODATABASE_FILE_1)
コア情報_削孔工程 (writer GEODATABASE_FILE_1)
    attributes: ボーリングID char(100), DTD_version char(8), 孔口標高 double(8,2), 測定年月日 date, 削孔深度 double(8,2), ケーシング下端深度 double(8,2)
孔径孔壁保護 (reader XML_1)
    attributes: xml_fragment xml_xml, xml_id xml_char(24), xml_matched_element xml_char(13), xml_parent_child_pos xml_char(1), xml_parent_id xml_char(1), ボーリング情報.DTD_version xml_decimal(4,2), 孔径孔壁保護_下端深度 xml_decimal(5,2), 孔径孔壁保護_孔径 xml_decimal(3,0), 孔径孔壁保護_孔壁保護コード xml_char(2), 孔径孔壁保護_孔壁保護実施理由 xml_char(5), 孔径孔壁保護_孔壁保護方法 xml_char(1)
    -> AttributeRemover_D_3
AttributeRemover_D_3
    REMOVE_ATTRS = xml_id,xml_matched_element,xml_parent_id,xml_parent_child_pos,ボーリング情報.DTD_version,xml_fragment
    -> BulkAttributeRenamer_D_3
BulkAttributeRenamer_D_3
    ATTRCHOICE = Selected Attributes
    ATTRLIST = 孔径孔壁保護_孔壁保護コード 孔径孔壁保護_孔径 孔径孔壁保護_孔壁保護実施理由 孔径孔壁保護_孔壁保護方法 孔径孔壁保護_下端深度
    CASE_DISP = YES
    MODE_CHOICE = RENAME
    PATTERN_ACTION_DISP = REMOVEPREFIX
    REPLACE_STR = 孔径孔壁保護_
    -> FeatureMerger_D_3 [REQUESTOR]
FeatureMerger_D_3
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_D_3
BulkAttributeTrimmerArcGISProVer_D_3
    -> 3DForcer_D_2
3DForcer_D_2
    KEEPZVAL = No
    ZVALATTR = @Value(孔口標高)-@Value(下端深度)
    -> AttributeRenamer_D_3
Note: AttributeRenamer_D_3 [AttributeRenamer] / Attributes To Rename: Input AttributeOutput AttributeDefault Value孔壁保護コード孔壁保護方法コード If Input Attribute Is Missing: Preserve Existing Output Attribute
AttributeRenamer_D_3
    ATTR_TABLE = RENAME_SET_DEFAULT 孔壁保護コード > 孔壁保護方法コード
    MISSING_INPUT_ATTRS = PRESERVE
    -> コア情報_孔径孔壁保護 (writer GEODATABASE_FILE_1)
コア情報_孔径孔壁保護 (writer GEODATABASE_FILE_1)
    attributes: ボーリングID char(100), DTD_version char(8), 孔口標高 double(8,2), 下端深度 double(8,2), 孔径 integer, 孔壁保護方法コード char(2), 孔壁保護方法 char(100), 孔壁保護実施理由 char(10)
Note: DTD version 2.10
掘進速度 (reader XML_1)
    attributes: xml_fragment xml_xml, xml_id xml_char(20), xml_matched_element xml_char(9), xml_parent_child_pos xml_char(1), xml_parent_id xml_char(1), ボーリング情報.DTD_version xml_decimal(4,2), 掘進速度_下端深度 xml_decimal(5,2), 掘進速度_掘進速度 xml_decimal(4,0)
    -> AttributeRemover_D_4
Note: DTD version 3.00, 4.00
削孔速度 (reader XML_1)
    attributes: xml_fragment xml_xml, xml_id xml_char(20), xml_matched_element xml_char(9), xml_parent_child_pos xml_char(1), xml_parent_id xml_char(1), ボーリング情報.DTD_version xml_decimal(4,2), 削孔速度_下端深度 xml_decimal(5,2), 削孔速度_削孔速度 xml_decimal(4,0)
    -> AttributeRemover_D_4
AttributeRemover_D_4
    REMOVE_ATTRS = xml_id,xml_matched_element,xml_parent_id,xml_parent_child_pos,ボーリング情報.DTD_version,xml_fragment
    -> BulkAttributeRenamer_D_4
BulkAttributeRenamer_D_4
    ATTRCHOICE = Selected Attributes
    ATTRLIST = 掘進速度_下端深度 削孔速度_削孔速度 掘進速度_掘進速度 削孔速度_下端深度
    MODE_CHOICE = RENAME
    PATTERN_ACTION_DISP = PCREGEXPREPLACE
    REPLACE_PATTERN = ^.+?_(.+)$
    REPLACE_STR = \1
    -> AttributeRenamer_D_4
AttributeRenamer_D_4
    ATTR_TABLE = RENAME_SET_DEFAULT 掘進速度 > 削孔速度
    MISSING_INPUT_ATTRS = PRESERVE
    -> FeatureMerger_D_4 [REQUESTOR]
FeatureMerger_D_4
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_D_4
BulkAttributeTrimmerArcGISProVer_D_4
    -> 3DForcer_D_3
3DForcer_D_3
    KEEPZVAL = No
    ZVALATTR = @Value(孔口標高)-@Value(下端深度)
    -> コア情報_削孔速度 (writer GEODATABASE_FILE_1)
コア情報_削孔速度 (writer GEODATABASE_FILE_1)
    attributes: ボーリングID char(100), DTD_version char(8), 孔口標高 double(8,2), 下端深度 double(8,2), 削孔速度 smallint
コアチューブビット (reader XML_1)
    attributes: xml_fragment xml_xml, xml_id xml_char(30), xml_matched_element xml_char(19), xml_parent_child_pos xml_char(1), xml_parent_id xml_char(1), コアチューブビット_コアチューブ名 xml_char(21), コアチューブビット_ビット名 xml_char(19), コアチューブビット_下端深度 xml_decimal(5,2), ボーリング情報.DTD_version xml_decimal(4,2)
    -> AttributeRemover_D_5
AttributeRemover_D_5
    REMOVE_ATTRS = xml_id,xml_matched_element,xml_parent_id,xml_parent_child_pos,ボーリング情報.DTD_version,xml_fragment
    -> BulkAttributeRenamer_D_5
BulkAttributeRenamer_D_5
    ATTRCHOICE = Selected Attributes
    ATTRLIST = コアチューブビット_ビット名 コアチューブビット_コアチューブ名 コアチューブビット_下端深度
    CASE_DISP = YES
    MODE_CHOICE = RENAME
    PATTERN_ACTION_DISP = REMOVEPREFIX
    REPLACE_STR = コアチューブビット_
    -> FeatureMerger_D_5 [REQUESTOR]
FeatureMerger_D_5
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_D_5
BulkAttributeTrimmerArcGISProVer_D_5
    -> 3DForcer_D_4
3DForcer_D_4
    KEEPZVAL = No
    ZVALATTR = @Value(孔口標高)-@Value(下端深度)
    -> コア情報_コアチューブビット (writer GEODATABASE_FILE_1)
コア情報_コアチューブビット (writer GEODATABASE_FILE_1)
    attributes: ボーリングID char(100), DTD_version char(8), 孔口標高 double(8,2), 下端深度 double(8,2), コアチューブ名 char(40), ビット名 char(40)
給圧条件 (reader XML_1)
    attributes: xml_fragment xml_xml, xml_id xml_char(20), xml_matched_element xml_char(9), xml_parent_child_pos xml_char(1), xml_parent_id xml_char(1), ボーリング情報.DTD_version xml_decimal(4,2), 給圧条件_下端深度 xml_decimal(5,2), 給圧条件_給圧 xml_decimal(3,1)
    -> AttributeRemover_D_6
AttributeRemover_D_6
    REMOVE_ATTRS = xml_id,xml_matched_element,xml_parent_id,xml_parent_child_pos,ボーリング情報.DTD_version,xml_fragment
    -> BulkAttributeRenamer_D_6
BulkAttributeRenamer_D_6
    ATTRCHOICE = Selected Attributes
    ATTRLIST = 給圧条件_下端深度 給圧条件_給圧
    CASE_DISP = YES
    MODE_CHOICE = RENAME
    PATTERN_ACTION_DISP = REMOVEPREFIX
    REPLACE_STR = 給圧条件_
    -> FeatureMerger_D_6 [REQUESTOR]
FeatureMerger_D_6
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_D_6
BulkAttributeTrimmerArcGISProVer_D_6
    -> 3DForcer_D_5
3DForcer_D_5
    KEEPZVAL = No
    ZVALATTR = @Value(孔口標高)-@Value(下端深度)
    -> コア情報_給圧条件 (writer GEODATABASE_FILE_1)
コア情報_給圧条件 (writer GEODATABASE_FILE_1)
    attributes: ボーリングID char(100), DTD_version char(8), 孔口標高 double(8,2), 下端深度 double(8,2), 給圧 double(8,1)
回転数 (reader XML_1)
    attributes: xml_fragment xml_xml, xml_id xml_char(18), xml_matched_element xml_char(7), xml_parent_child_pos xml_char(1), xml_parent_id xml_char(1), ボーリング情報.DTD_version xml_decimal(4,2), 回転数_下端深度 xml_decimal(5,2), 回転数_回転数 xml_decimal(4,0)
    -> AttributeRemover_D_7
AttributeRemover_D_7
    REMOVE_ATTRS = xml_id,xml_matched_element,xml_parent_id,xml_parent_child_pos,ボーリング情報.DTD_version,xml_fragment
    -> BulkAttributeRenamer_D_7
BulkAttributeRenamer_D_7
    ATTRCHOICE = Selected Attributes
    ATTRLIST = 回転数_下端深度 回転数_回転数
    CASE_DISP = YES
    MODE_CHOICE = RENAME
    PATTERN_ACTION_DISP = REMOVEPREFIX
    REPLACE_STR = 回転数_
    -> FeatureMerger_D_7 [REQUESTOR]
FeatureMerger_D_7
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_D_7
BulkAttributeTrimmerArcGISProVer_D_7
    -> 3DForcer_D_6
3DForcer_D_6
    KEEPZVAL = No
    ZVALATTR = @Value(孔口標高)-@Value(下端深度)
    -> コア情報_回転数 (writer GEODATABASE_FILE_1)
コア情報_回転数 (writer GEODATABASE_FILE_1)
    attributes: ボーリングID char(100), DTD_version char(8), 孔口標高 double(8,2), 下端深度 double(8,2), 回転数 smallint
送水条件 (reader XML_1)
    attributes: xml_fragment xml_xml, xml_id xml_char(20), xml_matched_element xml_char(9), xml_parent_child_pos xml_char(1), xml_parent_id xml_char(1), ボーリング情報.DTD_version xml_decimal(4,2), 送水条件_下端深度 xml_decimal(5,2), 送水条件_送水圧 xml_decimal(3,1), 送水条件_送水種類 xml_char(1), 送水条件_送水種類コード xml_decimal(2,0), 送水条件_送水量 xml_decimal(3,0), 送水条件_排水量 xml_decimal(3,0)
    -> AttributeRemover_D_8
AttributeRemover_D_8
    REMOVE_ATTRS = xml_id,xml_matched_element,xml_parent_id,xml_parent_child_pos,ボーリング情報.DTD_version,xml_fragment
    -> BulkAttributeRenamer_D_8
BulkAttributeRenamer_D_8
    ATTRCHOICE = Selected Attributes
    ATTRLIST = 送水条件_下端深度 送水条件_送水種類コード 送水条件_送水圧 送水条件_排水量 送水条件_送水種類 送水条件_送水量
    CASE_DISP = YES
    MODE_CHOICE = RENAME
    PATTERN_ACTION_DISP = REMOVEPREFIX
    REPLACE_STR = 送水条件_
    -> FeatureMerger_D_8 [REQUESTOR]
FeatureMerger_D_8
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_D_8
BulkAttributeTrimmerArcGISProVer_D_8
    -> 3DForcer_D_7
3DForcer_D_7
    KEEPZVAL = No
    ZVALATTR = @Value(孔口標高)-@Value(下端深度)
    -> コア情報_送水条件 (writer GEODATABASE_FILE_1)
コア情報_送水条件 (writer GEODATABASE_FILE_1)
    attributes: ボーリングID char(100), DTD_version char(8), 孔口標高 double(8,2), 下端深度 double(8,2), 送水圧 double(8,1), 送水量 smallint, 排水量 smallint, 送水種類コード char(2), 送水種類 char(100)
断層破砕帯区分 (reader XML_1)
    attributes: xml_fragment xml_xml, xml_id xml_char(26), xml_matched_element xml_char(15), xml_parent_child_pos xml_char(1), xml_parent_id xml_char(1), ボーリング情報.DTD_version xml_decimal(4,2), 断層破砕帯区分_下端深度 xml_decimal(5,2), 断層破砕帯区分_上端深度 xml_decimal(5,2), 断層破砕帯区分_性状 xml_char(7), 断層破砕帯区分_性状コード xml_decimal(2,0), 断層破砕帯区分_備考 xml_char(1)
    -> AttributeRemover_D_9
AttributeRemover_D_9
    REMOVE_ATTRS = xml_parent_child_pos,ボーリング情報.DTD_version,xml_parent_id,xml_id,xml_fragment,xml_matched_element
    -> BulkAttributeRenamer_D_9
BulkAttributeRenamer_D_9
    ATTRCHOICE = Selected Attributes
    ATTRLIST = 断層破砕帯区分_上端深度 断層破砕帯区分_下端深度 断層破砕帯区分_備考 断層破砕帯区分_性状 断層破砕帯区分_性状コード
    CASE_DISP = YES
    MODE_CHOICE = RENAME
    PATTERN_ACTION_DISP = REMOVEPREFIX
    REPLACE_STR = 断層破砕帯区分_
    -> FeatureMerger_D_9 [REQUESTOR]
FeatureMerger_D_9
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_D_9
BulkAttributeTrimmerArcGISProVer_D_9
    -> 3DForcer_D_8
3DForcer_D_8
    KEEPZVAL = No
    ZVALATTR = @Value(孔口標高)-@Value(下端深度)
    -> コア情報_断層破砕帯区分 (writer GEODATABASE_FILE_1)
コア情報_断層破砕帯区分 (writer GEODATABASE_FILE_1)
    attributes: ボーリングID char(100), DTD_version char(8), 孔口標高 double(8,2), 上端深度 double(8,2), 下端深度 double(8,2), 性状コード char(2), 性状 char(100), 備考 char(100)
コア採取率 (reader XML_1)
    attributes: xml_fragment xml_xml, xml_id xml_char(22), xml_matched_element xml_char(11), xml_parent_child_pos xml_char(1), xml_parent_id xml_char(1), コア採取率_下端深度 xml_decimal(4,2), コア採取率_採取率 xml_decimal(4,0), ボーリング情報.DTD_version xml_decimal(4,2)
    -> AttributeRemover_D_10
AttributeRemover_D_10
    REMOVE_ATTRS = xml_parent_child_pos,ボーリング情報.DTD_version,xml_parent_id,xml_id,xml_fragment,xml_matched_element
    -> BulkAttributeRenamer_D_10
BulkAttributeRenamer_D_10
    ATTRCHOICE = Selected Attributes
    ATTRLIST = コア採取率_採取率 コア採取率_下端深度
    CASE_DISP = YES
    MODE_CHOICE = RENAME
    PATTERN_ACTION_DISP = REMOVEPREFIX
    REPLACE_STR = コア採取率_
    -> FeatureMerger_D_10 [REQUESTOR]
FeatureMerger_D_10
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_D_10
BulkAttributeTrimmerArcGISProVer_D_10
    -> 3DForcer_D_9
3DForcer_D_9
    KEEPZVAL = No
    ZVALATTR = @Value(孔口標高)-@Value(下端深度)
    -> コア情報_コア採取率 (writer GEODATABASE_FILE_1)
コア情報_コア採取率 (writer GEODATABASE_FILE_1)
    attributes: ボーリングID char(100), DTD_version char(8), 孔口標高 double(8,2), 下端深度 double(8,2), 採取率 smallint
最大コア長 (reader XML_1)
    attributes: xml_fragment xml_xml, xml_id xml_char(22), xml_matched_element xml_char(11), xml_parent_child_pos xml_char(1), xml_parent_id xml_char(1), ボーリング情報.DTD_version xml_decimal(4,2), 最大コア長_コア長 xml_decimal(3,0), 最大コア長_下端深度 xml_decimal(4,2)
    -> AttributeRemover_D_11
AttributeRemover_D_11
    REMOVE_ATTRS = xml_parent_child_pos,ボーリング情報.DTD_version,xml_parent_id,xml_id,xml_fragment,xml_matched_element
    -> BulkAttributeRenamer_D_11
BulkAttributeRenamer_D_11
    ATTRCHOICE = Selected Attributes
    ATTRLIST = 最大コア長_コア長 最大コア長_下端深度
    CASE_DISP = YES
    MODE_CHOICE = RENAME
    PATTERN_ACTION_DISP = REMOVEPREFIX
    REPLACE_STR = 最大コア長_
    -> FeatureMerger_D_11 [REQUESTOR]
FeatureMerger_D_11
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_D_11
BulkAttributeTrimmerArcGISProVer_D_11
    -> 3DForcer_D_10
3DForcer_D_10
    KEEPZVAL = No
    ZVALATTR = @Value(孔口標高)-@Value(下端深度)
    -> AttributeRenamer_D_5
Note: AttributeRenamer_D_5 [AttributeRenamer] / Attributes To Rename: Input AttributeOutput AttributeDefault Valueコア長最大コア長 If Input Attribute Is Missing: Preserve Existing Output Attribute
AttributeRenamer_D_5
    ATTR_TABLE = RENAME_SET_DEFAULT コア長 > 最大コア長
    MISSING_INPUT_ATTRS = PRESERVE
    -> コア情報_最大コア長 (writer GEODATABASE_FILE_1)
コア情報_最大コア長 (writer GEODATABASE_FILE_1)
    attributes: ボーリングID char(100), DTD_version char(8), 孔口標高 double(8,2), 下端深度 double(8,2), 最大コア長 smallint
RQD (reader XML_1)
    attributes: RQD_RQD xml_decimal(3,0), RQD_下端深度 xml_decimal(5,2), xml_fragment xml_xml, xml_id xml_char(15), xml_matched_element xml_char(4), xml_parent_child_pos xml_char(1), xml_parent_id xml_char(1), ボーリング情報.DTD_version xml_decimal(4,2)
    -> AttributeRemover_D_12
AttributeRemover_D_12
    REMOVE_ATTRS = xml_parent_child_pos,ボーリング情報.DTD_version,xml_parent_id,xml_id,xml_fragment,xml_matched_element
    -> BulkAttributeRenamer_D_12
BulkAttributeRenamer_D_12
    ATTRCHOICE = Selected Attributes
    ATTRLIST = RQD_RQD RQD_下端深度
    CASE_DISP = YES
    MODE_CHOICE = RENAME
    PATTERN_ACTION_DISP = REMOVEPREFIX
    REPLACE_STR = RQD_
    -> FeatureMerger_D_12 [REQUESTOR]
FeatureMerger_D_12
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_D_12
BulkAttributeTrimmerArcGISProVer_D_12
    -> 3DForcer_D_11
3DForcer_D_11
    KEEPZVAL = No
    ZVALATTR = @Value(孔口標高)-@Value(下端深度)
    -> コア情報_RQD (writer GEODATABASE_FILE_1)
コア情報_RQD (writer GEODATABASE_FILE_1)
    attributes: ボーリングID char(100), DTD_version char(8), 孔口標高 double(8,2), 下端深度 double(8,2), RQD smallint
コア質量 (reader XML_1)
    attributes: xml_fragment xml_xml, xml_id xml_char(20), xml_matched_element xml_char(9), xml_parent_child_pos xml_char(1), xml_parent_id xml_char(1), コア質量_コア質量 xml_decimal(4,1), コア質量_下端深度 xml_decimal(5,2), ボーリング情報.DTD_version xml_decimal(4,2)
    -> AttributeRemover_D_13
AttributeRemover_D_13
    REMOVE_ATTRS = xml_parent_child_pos,ボーリング情報.DTD_version,xml_parent_id,xml_id,xml_fragment,xml_matched_element
    -> BulkAttributeRenamer_D_13
BulkAttributeRenamer_D_13
    ATTRCHOICE = Selected Attributes
    ATTRLIST = コア質量_コア質量 コア質量_下端深度
    CASE_DISP = YES
    MODE_CHOICE = RENAME
    PATTERN_ACTION_DISP = REMOVEPREFIX
    REPLACE_STR = コア質量_
    -> FeatureMerger_D_13 [REQUESTOR]
FeatureMerger_D_13
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_D_13
BulkAttributeTrimmerArcGISProVer_D_13
    -> 3DForcer_D_12
3DForcer_D_12
    KEEPZVAL = No
    ZVALATTR = @Value(孔口標高)-@Value(下端深度)
    -> コア情報_コア質量 (writer GEODATABASE_FILE_1)
コア情報_コア質量 (writer GEODATABASE_FILE_1)
    attributes: ボーリングID char(100), DTD_version char(8), 孔口標高 double(8,2), 下端深度 double(8,2), コア質量 double(8,1)
Note: DTD version 4.00
トレーサーによる地下水流動層検層詳細データ (reader XML_1)
    attributes: xml_fragment xml_xml, xml_id xml_char(54), xml_matched_element xml_char(43), xml_parent_child_pos xml_char(1), xml_parent_id xml_char(1), トレーサーによる地下水流動層検層詳細データ_検層番号 xml_decimal(5,0), トレーサーによる地下水流動層検層詳細データ_測定深度 xml_decimal(5,2), トレーサーによる地下水流動層検層詳細データ_比抵抗値{} xml_decimal(6,2), ボーリング情報.DTD_version xml_decimal(4,2)
    -> AttributeRemover_E_4
Note: DTD version 4.00
トレーサーによる地下水流動層検層判定結果 (reader XML_1)
    attributes: xml_fragment xml_xml, xml_id xml_char(52), xml_matched_element xml_char(41), xml_parent_child_pos xml_char(1), xml_parent_id xml_char(1), トレーサーによる地下水流動層検層判定結果_下端深度 xml_decimal(5,2), トレーサーによる地下水流動層検層判定結果_上端深度 xml_decimal(5,2), トレーサーによる地下水流動層検層判定結果_地下水流動層検層結果 xml_char(13), ボーリング情報.DTD_version xml_decimal(4,2)
    -> AttributeRemover_E_5
Note: DTD version 4.00
トレーサーによる地下水流動層検層 (reader XML_1)
    attributes: xml_fragment xml_xml, xml_id xml_char(44), xml_matched_element xml_char(33), xml_parent_child_pos xml_char(1), xml_parent_id xml_char(1), トレーサーによる地下水流動層検層_下端深度 xml_decimal(5,2), トレーサーによる地下水流動層検層_検層番号 xml_decimal(5,0), トレーサーによる地下水流動層検層_検層方法コード xml_decimal(2,0), トレーサーによる地下水流動層検層_孔内水位 xml_decimal(5,2), トレーサーによる地下水流動層検層_削孔深度 xml_decimal(5,2), トレーサーによる地下水流動層検層_上端深度 xml_decimal(5,2), トレーサーによる地下水流動層検層_測定時間{} xml_decimal(3,0), トレーサーによる地下水流動層検層_電解質溶液濃度 xml_decimal(3,1), ボーリング情報.DTD_version xml_decimal(4,2)
    -> AttributeRemover_E_3
Note: DTD version 2.10, 3.00
地下水検層試験詳細データ (reader XML_1)
    attributes: xml_fragment xml_xml, xml_id xml_char(36), xml_matched_element xml_char(25), xml_parent_child_pos xml_char(1), xml_parent_id xml_char(1), ボーリング情報.DTD_version xml_decimal(4,2), 地下水検層試験詳細データ_試験番号 xml_decimal(5,0), 地下水検層試験詳細データ_測定深度 xml_decimal(5,2), 地下水検層試験詳細データ_比抵抗値{} xml_decimal(6,0)
    -> AttributeRemover_E_4
AttributeRemover_E_4
    REMOVE_ATTRS = xml_parent_child_pos,ボーリング情報.DTD_version,xml_parent_id,xml_id,xml_fragment,xml_matched_element
    -> BulkAttributeRenamer_E_4
BulkAttributeRenamer_E_4
    ATTRCHOICE = All Attributes
    MODE_CHOICE = RENAME
    PATTERN_ACTION_DISP = PCREGEXPREPLACE
    REPLACE_PATTERN = ^.*地下水.+?_(.+)$
    REPLACE_STR = \1
    -> AttributeRenamer_E_2
AttributeRenamer_E_2
    ATTR_TABLE = RENAME_SET_DEFAULT 試験番号 > 検層番号
    MISSING_INPUT_ATTRS = PRESERVE
    -> FeatureMerger_E_4 [REQUESTOR]
FeatureMerger_E_4
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> AttributeManager_7
AttributeManager_7
    ATTR_TABLE = SET_TO 比抵抗値 = @Value(比抵抗値{0})
    -> BulkAttributeTrimmerArcGISProVer_E_4
BulkAttributeTrimmerArcGISProVer_E_4
    -> 3DForcer_E_4
3DForcer_E_4
    KEEPZVAL = No
    ZVALATTR = @Value(孔口標高)-@Value(測定深度)
    -> コア情報_地下水流動層検層詳細データ (writer GEODATABASE_FILE_1)
コア情報_地下水流動層検層詳細データ (writer GEODATABASE_FILE_1)
    attributes: ボーリングID char(100), DTD_version char(8), 孔口標高 double(8,2), 検層番号 char(4), 測定深度 double(8,2), 比抵抗値 char(2048)
Note: DTD version 2.10, 3.00
地下水検層試験判定結果 (reader XML_1)
    attributes: xml_fragment xml_xml, xml_id xml_char(34), xml_matched_element xml_char(23), xml_parent_child_pos xml_char(1), xml_parent_id xml_char(1), ボーリング情報.DTD_version xml_decimal(4,2), 地下水検層試験判定結果_下端深度 xml_decimal(5,2), 地下水検層試験判定結果_上端深度 xml_decimal(5,2), 地下水検層試験判定結果_地下水検層結果 xml_char(13)
    -> AttributeRemover_E_5
AttributeRemover_E_5
    REMOVE_ATTRS = xml_parent_child_pos,ボーリング情報.DTD_version,xml_parent_id,xml_id,xml_fragment,xml_matched_element
    -> BulkAttributeRenamer_E_5
BulkAttributeRenamer_E_5
    ATTRCHOICE = All Attributes
    MODE_CHOICE = RENAME
    PATTERN_ACTION_DISP = PCREGEXPREPLACE
    REPLACE_PATTERN = ^.*地下水.+?_(.+)$
    REPLACE_STR = \1
    -> AttributeRenamer_E_3
AttributeRenamer_E_3
    ATTR_TABLE = RENAME_SET_DEFAULT 地下水検層結果 > 地下水流動層検層結果
    MISSING_INPUT_ATTRS = PRESERVE
    -> FeatureMerger_E_5 [REQUESTOR]
FeatureMerger_E_5
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_E_5
BulkAttributeTrimmerArcGISProVer_E_5
    -> 3DForcer_E_5
3DForcer_E_5
    KEEPZVAL = No
    ZVALATTR = @Value(孔口標高)-@Value(下端深度)
    -> コア情報_地下水流動層検層判定結果 (writer GEODATABASE_FILE_1)
コア情報_地下水流動層検層判定結果 (writer GEODATABASE_FILE_1)
    attributes: ボーリングID char(100), DTD_version char(8), 孔口標高 double(8,2), 上端深度 double(8,2), 下端深度 double(8,2), 地下水流動層検層結果 char(100)
Note: DTD version 4.00
工学的地質区分名現場土質名 (reader XML_1)
    attributes: xml_fragment xml_xml, xml_id xml_char(37), xml_matched_element xml_char(27), xml_parent_child_pos xml_char(1), xml_parent_id xml_char(1), ボーリング情報.DTD_version xml_decimal(4,2), 工学的地質区分名現場土質名_下端深度 xml_decimal(5,2), 工学的地質区分名現場土質名_岩石群{}.工学的地質区分名現場土質名_岩石群コード xml_decimal(2,0), 工学的地質区分名現場土質名_岩石群{}.工学的地質区分名現場土質名_岩石土コード{}.工学的地質区分名現場土質名_岩石 xml_decimal(10,0), 工学的地質区分名現場土質名_岩石群{}.工学的地質区分名現場土質名_岩石土コード{}.工学的地質区分名現場土質名_岩相 xml_char(10), 工学的地質区分名現場土質名_岩石群{}.工学的地質区分名現場土質名_岩石土コード{}.工学的地質区分名現場土質名_変成岩岩石 xml_char(1), 工学的地質区分名現場土質名_岩石群{}.工学的地質区分名現場土質名_岩石土コード{}.工学的地質区分名現場土質名_変成岩岩相 xml_char(1), 工学的地質区分名現場土質名_工学的地質区分名現場土質名 xml_char(15), 工学的地質区分名現場土質名_工学的地質区分名現場土質名記号 xml_char(5)
    -> AttributeRemover_Z_2
保孔管 (reader XML_1)
    attributes: xml_fragment xml_xml, xml_id xml_char(18), xml_matched_element xml_char(7), xml_parent_child_pos xml_char(1), xml_parent_id xml_char(1), ボーリング情報.DTD_version xml_decimal(4,2), 保孔管_下端深度 xml_decimal(5,2), 保孔管_種別コード xml_decimal(2,0), 保孔管_備考 xml_char(29)
    -> AttributeRemover_E
AttributeRemover_E
    REMOVE_ATTRS = xml_id,xml_matched_element,xml_parent_id,xml_parent_child_pos,ボーリング情報.DTD_version,xml_fragment
    -> BulkAttributeRenamer_E
BulkAttributeRenamer_E
    ATTRCHOICE = Selected Attributes
    ATTRLIST = 保孔管_下端深度 保孔管_備考 保孔管_種別コード
    CASE_DISP = YES
    MODE_CHOICE = RENAME
    PATTERN_ACTION_DISP = REMOVEPREFIX
    REPLACE_STR = 保孔管_
    -> FeatureMerger_E [REQUESTOR]
FeatureMerger_E
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_E
BulkAttributeTrimmerArcGISProVer_E
    -> 3DForcer_E
3DForcer_E
    KEEPZVAL = No
    ZVALATTR = @Value(孔口標高)-@Value(下端深度)
    -> コア情報_保孔管 (writer GEODATABASE_FILE_1)
コア情報_保孔管 (writer GEODATABASE_FILE_1)
    attributes: ボーリングID char(100), DTD_version char(8), 孔口標高 double(8,2), 下端深度 double(8,2), 種別コード char(2), 備考 char(100)
計測機器 (reader XML_1)
    attributes: xml_fragment xml_xml, xml_id xml_char(20), xml_matched_element xml_char(9), xml_parent_child_pos xml_char(1), xml_parent_id xml_char(1), ボーリング情報.DTD_version xml_decimal(4,2), 計測機器_下端深度 xml_decimal(5,2), 計測機器_機器種別 xml_char(11), 計測機器_上端深度 xml_decimal(5,2), 計測機器_備考 xml_char(1)
    -> AttributeRemover_E_2
AttributeRemover_E_2
    REMOVE_ATTRS = xml_id,xml_matched_element,xml_parent_id,xml_parent_child_pos,ボーリング情報.DTD_version,xml_fragment
    -> BulkAttributeRenamer_E_2
BulkAttributeRenamer_E_2
    ATTRCHOICE = Selected Attributes
    ATTRLIST = 計測機器_上端深度 計測機器_機器種別 計測機器_備考 計測機器_下端深度
    CASE_DISP = YES
    MODE_CHOICE = RENAME
    PATTERN_ACTION_DISP = REMOVEPREFIX
    REPLACE_STR = 計測機器_
    -> FeatureMerger_E_2 [REQUESTOR]
FeatureMerger_E_2
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_E_2
BulkAttributeTrimmerArcGISProVer_E_2
    -> 3DForcer_E_2
3DForcer_E_2
    KEEPZVAL = No
    ZVALATTR = @Value(孔口標高)-@Value(下端深度)
    -> コア情報_計測機器 (writer GEODATABASE_FILE_1)
コア情報_計測機器 (writer GEODATABASE_FILE_1)
    attributes: ボーリングID char(100), DTD_version char(8), 孔口標高 double(8,2), 上端深度 double(8,2), 下端深度 double(8,2), 機器種別 char(100), 備考 char(100)
Note: DTD version 2.10, 3.00
地下水検層試験 (reader XML_1)
    attributes: xml_fragment xml_xml, xml_id xml_char(26), xml_matched_element xml_char(15), xml_parent_child_pos xml_char(1), xml_parent_id xml_char(1), ボーリング情報.DTD_version xml_decimal(4,2), 地下水検層試験_下端深度 xml_decimal(5,2), 地下水検層試験_掘削深度 xml_decimal(5,2), 地下水検層試験_孔内水位 xml_decimal(5,2), 地下水検層試験_試験番号 xml_decimal(5,0), 地下水検層試験_試験方法コード xml_decimal(2,0), 地下水検層試験_上端深度 xml_decimal(5,2), 地下水検層試験_測定時間{} xml_decimal(4,0), 地下水検層試験_電解質溶液濃度 xml_decimal(3,1)
    -> AttributeRemover_E_3
AttributeRemover_E_3
    REMOVE_ATTRS = xml_parent_child_pos,ボーリング情報.DTD_version,xml_parent_id,xml_id,xml_fragment,xml_matched_element
    -> BulkAttributeRenamer_E_3
BulkAttributeRenamer_E_3
    ATTRCHOICE = All Attributes
    MODE_CHOICE = RENAME
    PATTERN_ACTION_DISP = PCREGEXPREPLACE
    REPLACE_PATTERN = ^.*地下水.+?_(.+)$
    REPLACE_STR = \1
    -> AttributeRenamer_E
AttributeRenamer_E
    ATTR_TABLE:
      RENAME_SET_DEFAULT 試験番号 > 検層番号
      RENAME_SET_DEFAULT 掘削深度 > 削孔深度
      RENAME_SET_DEFAULT 試験方法コード > 検層方法コード
    MISSING_INPUT_ATTRS = PRESERVE
    -> FeatureMerger_E_3 [REQUESTOR]
FeatureMerger_E_3
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> AttributeManager_6
AttributeManager_6
    ATTR_TABLE:
      SET_TO 測定時間
      SET_TO = @Value(測定時間{0})
    -> BulkAttributeTrimmerArcGISProVer_E_3
BulkAttributeTrimmerArcGISProVer_E_3
    -> 3DForcer_E_3
3DForcer_E_3
    KEEPZVAL = No
    ZVALATTR = @Value(孔口標高)-@Value(下端深度)
    -> コア情報_地下水流動層検層 (writer GEODATABASE_FILE_1)
コア情報_地下水流動層検層 (writer GEODATABASE_FILE_1)
    attributes: ボーリングID char(100), DTD_version char(8), 孔口標高 double(8,2), 検層番号 char(4), 上端深度 double(8,2), 下端深度 double(8,2), 削孔深度 double(8,2), 孔内水位 double(8,2), 検層方法コード char(2), 電解質溶液濃度 double(6,1), 測定時間 char(2048)
備考 (reader XML_1)
    attributes: xml_fragment xml_xml, xml_id xml_char(16), xml_matched_element xml_char(5), xml_parent_child_pos xml_char(1), xml_parent_id xml_char(1), ボーリング情報.DTD_version xml_decimal(4,2), 備考_タイトル xml_char(17), 備考_下端深度 xml_decimal(5,2), 備考_上端深度 xml_decimal(5,2), 備考_備考内容 xml_char(9)
    -> AttributeRemover_E_6
AttributeRemover_E_6
    REMOVE_ATTRS = xml_parent_child_pos,ボーリング情報.DTD_version,xml_parent_id,xml_id,xml_fragment,xml_matched_element
    -> BulkAttributeRenamer_E_6
BulkAttributeRenamer_E_6
    ATTRCHOICE = Selected Attributes
    ATTRLIST = 備考_上端深度 備考_備考内容 備考_タイトル 備考_下端深度
    CASE_DISP = YES
    MODE_CHOICE = RENAME
    PATTERN_ACTION_DISP = REMOVEPREFIX
    REPLACE_STR = 備考_
    -> FeatureMerger_E_6 [REQUESTOR]
FeatureMerger_E_6
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_E_6
BulkAttributeTrimmerArcGISProVer_E_6
    -> 3DForcer_E_6
3DForcer_E_6
    KEEPZVAL = No
    ZVALATTR = @Value(孔口標高)-@Value(下端深度)
    -> コア情報_備考 (writer GEODATABASE_FILE_1)
コア情報_備考 (writer GEODATABASE_FILE_1)
    attributes: ボーリングID char(100), DTD_version char(8), 孔口標高 double(8,2), タイトル char(100), 上端深度 double(8,2), 下端深度 double(8,2), 備考内容 char(200)
Note: DTD version 2.10
土質岩種区分 (reader XML_1)
    attributes: xml_fragment xml_xml, xml_id xml_char(23), xml_matched_element xml_char(13), xml_parent_child_pos xml_char(1), xml_parent_id xml_char(1), ボーリング情報.DTD_version xml_decimal(4,2), 土質岩種区分_下端深度 xml_decimal(5,2), 土質岩種区分_土質岩種記号1 xml_char(4), 土質岩種区分_土質岩種記号2 xml_char(1), 土質岩種区分_土質岩種区分1 xml_char(15), 土質岩種区分_土質岩種区分2 xml_char(1), 土質岩種区分_分類コード1 xml_decimal(6,0), 土質岩種区分_分類コード2 xml_char(1)
    -> AttributeRemover_Z
AttributeRemover_Z
    REMOVE_ATTRS = xml_parent_child_pos,ボーリング情報.DTD_version,xml_parent_id,xml_id,xml_fragment,xml_matched_element
    -> BulkAttributeRenamer_Z
BulkAttributeRenamer_Z
    ATTRCHOICE = Selected Attributes
    ATTRLIST = 土質岩種区分_土質岩種区分1 土質岩種区分_土質岩種記号2 土質岩種区分_下端深度 土質岩種区分_分類コード2 土質岩種区分_分類コード1 土質岩種区分_土質岩種記号1 土質岩種区分_土質岩種区分2
    CASE_DISP = YES
    MODE_CHOICE = RENAME
    PATTERN_ACTION_DISP = REMOVEPREFIX
    REPLACE_STR = 土質岩種区分_
    -> FeatureMerger_Z [REQUESTOR]
FeatureMerger_Z
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_Z
BulkAttributeTrimmerArcGISProVer_Z
    -> 3DForcer_Z
3DForcer_Z
    KEEPZVAL = No
    ZVALATTR = @Value(孔口標高)-@Value(下端深度)
    -> コア情報_土質岩種区分 (writer GEODATABASE_FILE_1)
コア情報_土質岩種区分 (writer GEODATABASE_FILE_1)
    attributes: ボーリングID char(100), DTD_version char(8), 孔口標高 double(8,2), 下端深度 double(8,2), 土質岩種区分1 char(40), 土質岩種記号1 char(10), 分類コード1 char(10), 土質岩種区分2 char(40), 土質岩種記号2 char(10), 分類コード2 char(10)
Note: DTD vesion 3.00
岩石土区分 (reader XML_1)
    attributes: xml_fragment xml_xml, xml_id xml_char(21), xml_matched_element xml_char(11), xml_parent_child_pos xml_char(1), xml_parent_id xml_char(1), ボーリング情報.DTD_version xml_decimal(4,2), 岩石土区分_下端深度 xml_decimal(5,2), 岩石土区分_岩石群{}.岩石土区分_岩石群コード xml_decimal(2,0), 岩石土区分_岩石群{}.岩石土区分_岩石土コード{}.岩石土区分_岩石 xml_char(10), 岩石土区分_岩石群{}.岩石土区分_岩石土コード{}.岩石土区分_岩相 xml_char(10), 岩石土区分_岩石群{}.岩石土区分_岩石土コード{}.岩石土区分_変成岩岩石 xml_char(1), 岩石土区分_岩石群{}.岩石土区分_岩石土コード{}.岩石土区分_変成岩岩相 xml_char(1), 岩石土区分_岩石土記号 xml_char(5), 岩石土区分_岩石土名 xml_char(15)
    -> AttributeRemover_Z_2
AttributeRemover_Z_2
    REMOVE_ATTRS = xml_parent_child_pos,ボーリング情報.DTD_version,xml_parent_id,xml_id,xml_fragment,xml_matched_element
    -> BulkAttributeRenamer_Z_2
BulkAttributeRenamer_Z_2
    ATTRCHOICE = All Attributes
    MODE_CHOICE = RENAME
    PATTERN_ACTION_DISP = PCREGEXPREPLACE
    REPLACE_PATTERN = ^(岩石土区分|工学的地質区分名現場土質名)_(.+)$
    REPLACE_STR = \2
    -> ListExploder_Z
ListExploder_Z
    ATTR_ACCUM_MODE = Merge List Attributes
    ATTR_CONFLICT_RES = Use List Attribute Values
    LIST_ATTR = 岩石群{}
    ELEMENTS -> BulkAttributeRenamer_Z_3
BulkAttributeRenamer_Z_3
    ATTRCHOICE = All Attributes
    MODE_CHOICE = RENAME
    PATTERN_ACTION_DISP = PCREGEXPREPLACE
    REPLACE_PATTERN = ^(岩石土区分|工学的地質区分名現場土質名)_(.+)$
    REPLACE_STR = \2
    -> AttributeRenamer_Z
AttributeRenamer_Z
    ATTR_TABLE:
      RENAME_SET_DEFAULT 岩石土名 > 工学的地質区分名現場土質名
      RENAME_SET_DEFAULT 岩石土記号 > 工学的地質区分名現場土質名記号
    MISSING_INPUT_ATTRS = PRESERVE
    -> FeatureMerger_Z_2 [REQUESTOR]
FeatureMerger_Z_2
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> AttributeManager_5
AttributeManager_5
    ATTR_TABLE:
      SET_TO 岩石土コード_岩相 = FME_CONDITIONAL:DEFAULT_VALUE'_FME_NO_OP_'BOOL_OP;OR;COMPOSITE_TEST;1;TEST @Value(DTD_version) = 3'@Value(岩石土コード{0}.岩石土区分_岩相)'BOOL_OP;OR;COMPOSITE_TEST;1;TEST @Value(DTD_version) = 4'@Value(岩石土コード{0}.工学的地質区分名現場土質名_岩相)'FME_NUM_CONDITIONS3___
      SET_TO 岩石土コード_岩石 = FME_CONDITIONAL:DEFAULT_VALUE'_FME_NO_OP_'BOOL_OP;OR;COMPOSITE_TEST;1;TEST @Value(DTD_version) = 3'@Value(岩石土コード{0}.岩石土区分_岩石)'BOOL_OP;OR;COMPOSITE_TEST;1;TEST @Value(DTD_version) = 4'@Value(岩石土コード{0}.工学的地質区分名現場土質名_岩石)'FME_NUM_CONDITIONS3___
      SET_TO 岩石土コード_変成岩岩相 = FME_CONDITIONAL:DEFAULT_VALUE'_FME_NO_OP_'BOOL_OP;OR;COMPOSITE_TEST;1;TEST @Value(DTD_version) = 3'@Value(岩石土コード{0}.岩石土区分_変成岩岩相)'BOOL_OP;OR;COMPOSITE_TEST;1;TEST @Value(DTD_version) = 4'@Value(岩石土コード{0}.工学的地質区分名現場土質名_変成岩岩相)'FME_NUM_CONDITIONS3___
      SET_TO 岩石土コード_変成岩岩石 = FME_CONDITIONAL:DEFAULT_VALUE'_FME_NO_OP_'BOOL_OP;OR;COMPOSITE_TEST;1;TEST @Value(DTD_version) = 3'@Value(岩石土コード{0}.岩石土区分_変成岩岩石)'BOOL_OP;OR;COMPOSITE_TEST;1;TEST @Value(DTD_version) = 4'@Value(岩石土コード{0}.工学的地質区分名現場土質名_変成岩岩石)'FME_NUM_CONDITIONS3___
    -> BulkAttributeTrimmerArcGISProVer_E_8
BulkAttributeTrimmerArcGISProVer_E_8
    -> 3DForcer_Z_2
3DForcer_Z_2
    KEEPZVAL = No
    ZVALATTR = @Value(孔口標高)-@Value(下端深度)
    -> コア情報_工学的地質区分名現場土質名 (writer GEODATABASE_FILE_1)
コア情報_工学的地質区分名現場土質名 (writer GEODATABASE_FILE_1)
    attributes: ボーリングID char(100), DTD_version char(8), 孔口標高 double(8,2), 下端深度 double(8,2), 工学的地質区分名現場土質名 char(40), 工学的地質区分名現場土質名記号 char(10), 岩石群コード char(2), 岩石土コード_岩相 char(2048), 岩石土コード_岩石 char(2048), 岩石土コード_変成岩岩相 char(2048), 岩石土コード_変成岩岩石 char(2048)
フリー情報 (reader XML_1)
    attributes: xml_fragment xml_xml, xml_id xml_char(22), xml_matched_element xml_char(11), xml_parent_child_pos xml_char(1), xml_parent_id xml_char(1), フリー情報 xml_char(3), ボーリング情報.DTD_version xml_decimal(4,2)
    -> AttributeRemover_E_7
AttributeRemover_E_7
    REMOVE_ATTRS = xml_parent_child_pos,ボーリング情報.DTD_version,xml_parent_id,xml_id,xml_fragment,xml_matched_element
    -> FeatureMerger_E_7 [REQUESTOR]
FeatureMerger_E_7
    ATTR_ACCUM_MODE = Merge Supplier
    ATTR_CONFLICT_RES = Use Requestor
    IGNORE_NULLS = No
    JOIN_KEYS = @Value(fme_dataset) @Value(fme_dataset) AUTO
    MERGE_TYPE = Attributes and Geometry
    PROCESS_DUPS = NO
    REJECT_NULL_MISSING_KEYS = No
    SUPPLIERS_FIRST = No
    MERGED -> BulkAttributeTrimmerArcGISProVer_E_7
BulkAttributeTrimmerArcGISProVer_E_7
    -> コア情報_フリー情報 (writer GEODATABASE_FILE_1)
コア情報_フリー情報 (writer GEODATABASE_FILE_1)
    attributes: ボーリングID char(100), DTD_version char(8), 孔口標高 double(8,2), フリー情報 char(2048)

Bookmark: 3Dポイントジオメトリ作成, 座標系変換
Note: ポイントZ座標 = 孔口標高。ただし, コア情報各フィーチャータイプについては後で 3DForcer によって変更する。 / 座標系変換には, 国土地理院グリッドシフトパラメーターファイルを使用する。 / TKY2JGD.par: Tokyo Dataum -> JGD 2000 / touhokutaiheiyouoki2011.par: JGD2000 -> JGD2011
VertexCreator
    MEASURE_TYPE = Continuous
    MODE_NAME = Replace with Point
    XVAL = @Value(経度_度)+@Value(経度_分)/60.0+@Value(経度_秒)/3600.0
    YVAL = @Value(緯度_度)+@Value(緯度_分)/60.0+@Value(緯度_秒)/3600.0
    ZVAL = @Value(孔口標高)
    -> TestFilter
TestFilter
    DEFAULT_VALUE = <UNFILTERED>
    PASSED_TEST_GROUP_OUTPUT = FIRST
    TEST_LIST = BOOL_OP,OR,COMPOSITE_TEST,<Unused>,TEST_CLAUSE,"TEST @Value(測地系) = 0",Tokyo Datum,BOOL_OP,OR,COMPOSITE_TEST,<Unused>,TEST_CLAUSE,"TEST @Value(測地系) = 1",JGD2000,BOOL_OP,OR,COMPOSITE_TEST,<Unused>,TEST_CLAUSE,"TEST @Value(測地系) = 2",JGD2011
    Tokyo Datum -> CsmapReprojector
    JGD2000 -> CsmapReprojector_2
    JGD2011 -> CoordinateSystemSetter
Note: Tokyo Datum -> JGD2000
CsmapReprojector
    DEST = LL-JGD2K
    INTERPOLATION_TYPE_NAME = Nearest Neighbor
    RASTER_CELL_SIZE = Preserve Cells
    RASTER_TOLERANCE = 0.0
    SOURCE = Tokyo
    TRANSFORMATION = Tokyo-Grid_to_JGD2000
    REPROJECTED -> CsmapReprojector_2
Note: JGD2000 -> JGD2011
CsmapReprojector_2
    DEST = LL-JGD2011_FME
    INTERPOLATION_TYPE_NAME = Nearest Neighbor
    RASTER_CELL_SIZE = Preserve Cells
    RASTER_TOLERANCE = 0.0
    SOURCE = LL-JGD2K
    TRANSFORMATION = JGD2000_to_JGD2011
    REPROJECTED -> DateFormatter
CoordinateSystemSetter
    COORDSYS = LL-JGD2011_FME
    -> DateFormatter

Bookmark: DTD version 2.10, 3.00
コア形状区分 (reader XML_1)
    attributes: xml_fragment xml_xml, xml_id xml_char(23), xml_matched_element xml_char(13), xml_parent_child_pos xml_char(1), xml_parent_id xml_char(1), コア形状区分_コア形状区分 xml_decimal(4,0), コア形状区分_下端深度 xml_decimal(4,2), ボーリング情報.DTD_version xml_decimal(4,2)
    -> FeatureMerger_B_3 [REQUESTOR]
コア形状区分判定表 (reader XML_1)
    attributes: xml_fragment xml_xml, xml_id xml_char(29), xml_matched_element xml_char(19), xml_parent_child_pos xml_char(1), xml_parent_id xml_char(1), コア形状区分判定表_コード xml_decimal(4,0), コア形状区分判定表_記号 xml_char(5), コア形状区分判定表_区分 xml_char(9), コア形状区分判定表_説明 xml_char(78), ボーリング情報.DTD_version xml_decimal(4,2)
    -> FeatureMerger_B_3 [SUPPLIER]

Bookmark: DTD version 2.10, 3.00
割れ目区分 (reader XML_1)
    attributes: xml_fragment xml_xml, xml_id xml_char(22), xml_matched_element xml_char(11), xml_parent_child_pos xml_char(1), xml_parent_id xml_char(1), ボーリング情報.DTD_version xml_decimal(4,2), 割れ目区分_下端深度 xml_decimal(4,2), 割れ目区分_割れ目区分 xml_decimal(4,0)
    -> FeatureMerger_B_6 [REQUESTOR]
割れ目区分判定表 (reader XML_1)
    attributes: xml_fragment xml_xml, xml_id xml_char(28), xml_matched_element xml_char(17), xml_parent_child_pos xml_char(1), xml_parent_id xml_char(1), ボーリング情報.DTD_version xml_decimal(4,2), 割れ目区分判定表_コード xml_decimal(4,0), 割れ目区分判定表_記号 xml_char(2), 割れ目区分判定表_区分 xml_char(4), 割れ目区分判定表_説明 xml_char(4)
    -> FeatureMerger_B_6 [SUPPLIER]

Bookmark: DTD version 2.10, 3.00
風化区分 (reader XML_1)
    attributes: xml_fragment xml_xml, xml_id xml_char(20), xml_matched_element xml_char(9), xml_parent_child_pos xml_char(1), xml_parent_id xml_char(1), ボーリング情報.DTD_version xml_decimal(4,2), 風化区分_下端深度 xml_decimal(4,2), 風化区分_風化区分 xml_decimal(4,0)
    -> FeatureMerger_B_9 [REQUESTOR]
風化区分判定表 (reader XML_1)
    attributes: xml_fragment xml_xml, xml_id xml_char(26), xml_matched_element xml_char(15), xml_parent_child_pos xml_char(1), xml_parent_id xml_char(1), ボーリング情報.DTD_version xml_decimal(4,2), 風化区分判定表_コード xml_char(1), 風化区分判定表_記号 xml_char(1), 風化区分判定表_区分 xml_char(1), 風化区分判定表_説明 xml_char(1)
    -> FeatureMerger_B_9 [SUPPLIER]

Bookmark: DTD version 2.10, 3.00
変質区分 (reader XML_1)
    attributes: xml_fragment xml_xml, xml_id xml_char(20), xml_matched_element xml_char(9), xml_parent_child_pos xml_char(1), xml_parent_id xml_char(1), ボーリング情報.DTD_version xml_decimal(4,2), 変質区分_下端深度 xml_decimal(4,2), 変質区分_変質区分 xml_decimal(4,0)
    -> FeatureMerger_B_12 [REQUESTOR]
変質区分判定表 (reader XML_1)
    attributes: xml_fragment xml_xml, xml_id xml_char(26), xml_matched_element xml_char(15), xml_parent_child_pos xml_char(1), xml_parent_id xml_char(1), ボーリング情報.DTD_version xml_decimal(4,2), 変質区分判定表_コード xml_decimal(4,0), 変質区分判定表_記号 xml_decimal(2,0), 変質区分判定表_区分 xml_char(7), 変質区分判定表_説明 xml_char(255)
    -> FeatureMerger_B_12 [SUPPLIER]

Bookmark: DTD version 4.00
ボーリングコアの形状区分判定表 (reader XML_1)
    attributes: xml_fragment xml_xml, xml_id xml_char(41), xml_matched_element xml_char(31), xml_parent_child_pos xml_char(1), xml_parent_id xml_char(1), ボーリングコアの形状区分判定表_コード xml_decimal(4,0), ボーリングコアの形状区分判定表_記号 xml_char(5), ボーリングコアの形状区分判定表_区分 xml_char(9), ボーリングコアの形状区分判定表_説明 xml_char(78), ボーリング情報.DTD_version xml_decimal(4,2)
    -> FeatureMerger_B_4 [SUPPLIER]
ボーリングコアの形状区分 (reader XML_1)
    attributes: xml_fragment xml_xml, xml_id xml_char(35), xml_matched_element xml_char(25), xml_parent_child_pos xml_char(1), xml_parent_id xml_char(1), ボーリングコアの形状区分_ボーリングコアの形状区分 xml_decimal(4,0), ボーリングコアの形状区分_下端深度 xml_decimal(4,2), ボーリング情報.DTD_version xml_decimal(4,2)
    -> FeatureMerger_B_4 [REQUESTOR]

Bookmark: DTD versiont 4.00
割れ目の状態区分判定表 (reader XML_1)
    attributes: xml_fragment xml_xml, xml_id xml_char(34), xml_matched_element xml_char(23), xml_parent_child_pos xml_char(1), xml_parent_id xml_char(1), ボーリング情報.DTD_version xml_decimal(4,2), 割れ目の状態区分判定表_コード xml_decimal(4,0), 割れ目の状態区分判定表_記号 xml_char(2), 割れ目の状態区分判定表_区分 xml_char(4), 割れ目の状態区分判定表_説明 xml_char(4)
    -> FeatureMerger_B_7 [SUPPLIER]
割れ目の状態区分 (reader XML_1)
    attributes: xml_fragment xml_xml, xml_id xml_char(28), xml_matched_element xml_char(17), xml_parent_child_pos xml_char(1), xml_parent_id xml_char(1), ボーリング情報.DTD_version xml_decimal(4,2), 割れ目の状態区分_下端深度 xml_decimal(4,2), 割れ目の状態区分_割れ目の状態区分 xml_decimal(4,0)
    -> FeatureMerger_B_7 [REQUESTOR]

Bookmark: DTD version 4.00
風化の程度区分判定表 (reader XML_1)
    attributes: xml_fragment xml_xml, xml_id xml_char(32), xml_matched_element xml_char(21), xml_parent_child_pos xml_char(1), xml_parent_id xml_char(1), ボーリング情報.DTD_version xml_decimal(4,2), 風化の程度区分判定表_コード xml_decimal(4,0), 風化の程度区分判定表_記号 xml_char(2), 風化の程度区分判定表_区分 xml_char(4), 風化の程度区分判定表_説明 xml_char(4)
    -> FeatureMerger_B_10 [SUPPLIER]
風化の程度区分 (reader XML_1)
    attributes: xml_fragment xml_xml, xml_id xml_char(26), xml_matched_element xml_char(15), xml_parent_child_pos xml_char(1), xml_parent_id xml_char(1), ボーリング情報.DTD_version xml_decimal(4,2), 風化の程度区分_下端深度 xml_decimal(4,2), 風化の程度区分_風化の程度区分 xml_decimal(4,0)
    -> FeatureMerger_B_10 [REQUESTOR]

Bookmark: DTD version 4.00
熱水変質の程度区分判定表 (reader XML_1)
    attributes: xml_fragment xml_xml, xml_id xml_char(36), xml_matched_element xml_char(25), xml_parent_child_pos xml_char(1), xml_parent_id xml_char(1), ボーリング情報.DTD_version xml_decimal(4,2), 熱水変質の程度区分判定表_コード xml_decimal(4,0), 熱水変質の程度区分判定表_記号 xml_decimal(2,0), 熱水変質の程度区分判定表_区分 xml_char(7), 熱水変質の程度区分判定表_説明 xml_char(124)
    -> FeatureMerger_B_13 [SUPPLIER]
熱水変質の程度区分 (reader XML_1)
    attributes: xml_fragment xml_xml, xml_id xml_char(30), xml_matched_element xml_char(19), xml_parent_child_pos xml_char(1), xml_parent_id xml_char(1), ボーリング情報.DTD_version xml_decimal(4,2), 熱水変質の程度区分_下端深度 xml_decimal(4,2), 熱水変質の程度区分_熱水変質の程度区分 xml_decimal(4,0)
    -> FeatureMerger_B_13 [REQUESTOR]

FME custom transformer BulkAttributeTrimmerArcGISProVer

Input (input)
    -> TclCaller
TclCaller
    SRC:
      proc trimAll {} {
          foreach attr [FME_AttributeNames] {
              FME_SetAttribute $attr [string trim [FME_GetAttribute $attr]]
          }
      }
    TCLPROG = trimAll
    VAL_ATTR = _result
    -> Output (output)
Output (output)
